module sonic-frr-ospf {
    namespace "http://github.com/sonic-net/frr/sonic-frr-ospf";
    prefix frr-ospf;
    yang-version 1.1;

    import ietf-inet-types {
        prefix inet;
    }

    organization
        "SONiC";

    contact
        "SONiC";

    description
        "SONIC frr-ospf FRR YANG";

    revision 2024-12-23 {
        description
            "Initial revision.";
    }
    container sonic-frr-ospf {
        container OSPF_NODE {
            list NO {
                key "PREFIX";
                leaf PREFIX {
                    type string; 
                } 
                leaf area {
                    type enumeration {
                        enum area;
                    }
                }                  //area
                leaf OSPF_AREA_ID_IN {
                    type union {
                        type inet:ipv4-address;
                        type int32;
                    }
                }                  //<A.B.C.D|(0-4294967295)>
                leaf authentication {
                    type enumeration {
                        enum authentication;
                    }
                }                  //authentication
                leaf authentication_message-digest {
                    type enumeration {
                        enum authentication_message-digest;
                    }
                }                  //message-digest
                leaf default-cost {
                    type enumeration {
                        enum default-cost;
                    }
                }                  //default-cost
                leaf STUB_ADVERTISED_DEFAULT_SUMMARY {
                    type int32;
                }                  //(0-16777215)
                leaf export-list {
                    type enumeration {
                        enum export-list;
                    }
                }                  //export-list
                leaf NAME_OF_THE_ACCESS-LIST {
                    type string;
                }                  //ACCESSLIST4_NAME
                leaf filter-list_prefix {
                    type enumeration {
                        enum filter-list_prefix;
                    }
                }                  //prefix
                leaf NAME_OF_AN_IP {
                    type string;
                }                  //PREFIXLIST_NAME
                leaf IN_OUT_BOUND {
                    type enumeration {
                        enum in;
                        enum out;
                    }
                }                  //<in|out> ['Filter networks sent to this area', 'Filter networks sent from this area']
                leaf import-list {
                    type enumeration {
                        enum import-list;
                    }
                }                  //import-list
                leaf nssa {
                    type enumeration {
                        enum nssa;
                    }
                }                  //nssa
                leaf NSSA_TRANSLATE_MODE {
                    type enumeration {
                        enum translate-candidate;
                        enum translate-never;
                        enum translate-always;
                    }
                }                  //<translate-candidate|translate-never|translate-always> ['Configure NSSA-ABR for translate election (default)', 'Configure NSSA-ABR to never translate', 'Configure NSSA-ABR to always translate']
                leaf nssa_no-summary {
                    type enumeration {
                        enum nssa_no-summary;
                    }
                }                  //no-summary
                leaf nssa_suppress-fa {
                    type enumeration {
                        enum nssa_suppress-fa;
                    }
                }                  //suppress-fa
                leaf range {
                    type enumeration {
                        enum range;
                    }
                }                  //range
                leaf IPV4_PREFIX {
                    type inet:ipv4-prefix;
                }                  //A.B.C.D/M
                leaf cost {
                    type enumeration {
                        enum cost;
                    }
                }                  //cost
                leaf ADVERTISED_METRIC_FOR_THIS {
                    type int32;
                }                  //(0-16777215)
                leaf advertise {
                    type enumeration {
                        enum advertise;
                    }
                }                  //advertise
                leaf advertise_cost {
                    type enumeration {
                        enum advertise_cost;
                    }
                }                  //cost
                leaf not-advertise {
                    type enumeration {
                        enum not-advertise;
                    }
                }                  //not-advertise
                leaf substitute {
                    type enumeration {
                        enum substitute;
                    }
                }                  //substitute
                leaf shortcut {
                    type enumeration {
                        enum shortcut;
                    }
                }                  //shortcut
                leaf SHORTCUT_STATE {
                    type enumeration {
                        enum enable;
                        enum disable;
                    }
                }                  //<enable|disable> ['Deconfigure enabled shortcutting through the area', 'Deconfigure disabled shortcutting through the area']
                leaf stub {
                    type enumeration {
                        enum stub;
                    }
                }                  //stub
                leaf stub_no-summary {
                    type enumeration {
                        enum stub_no-summary;
                    }
                }                  //no-summary
                leaf virtual-link {
                    type enumeration {
                        enum virtual-link;
                    }
                }                  //virtual-link
                leaf ROUTER_ID_OF_THE {
                    type inet:ipv4-address;
                }                  //A.B.C.D
                leaf AUTHENTICATION_TYPE {
                    type enumeration {
                        enum message-digest;
                        enum null;
                    }
                }                  //<message-digest|null> ['Use message-digest authentication', 'Use null authentication']
                leaf message-digest-key {
                    type int32;
                }                  //(1-255)
                leaf md5 {
                    type string;
                }                  //KEY
                leaf authentication-key {
                    type string;
                }                  //AUTH_KEY
                leaf hello-interval {
                    type enumeration {
                        enum hello-interval;
                    }
                }                  //hello-interval
                leaf SECONDS {
                    type int32;
                }                  //(1-65535)
                leaf retransmit-interval {
                    type enumeration {
                        enum retransmit-interval;
                    }
                }                  //retransmit-interval
                leaf transmit-delay {
                    type enumeration {
                        enum transmit-delay;
                    }
                }                  //transmit-delay
                leaf dead-interval {
                    type enumeration {
                        enum dead-interval;
                    }
                }                  //dead-interval
                leaf distribute-list {
                    type enumeration {
                        enum distribute-list;
                    }
                }                  //distribute-list
                leaf ACCESS-LIST_NAME {
                    type string;
                }                  //ACCESSLIST4_NAME
                leaf out {
                    type enumeration {
                        enum out;
                    }
                }                  //out
                leaf FRR_REDIST_HELP_STR_OSPFD {
                    type string;
                }                  //FRR_REDIST_STR_OSPFD
                leaf maximum-paths {
                    type enumeration {
                        enum maximum-paths;
                    }
                }                  //maximum-paths
                leaf neighbor {
                    type enumeration {
                        enum neighbor;
                    }
                }                  //neighbor
                leaf NEIGHBOR_IP_ADDRESS {
                    type inet:ipv4-address;
                }                  //A.B.C.D
                leaf priority {
                    type enumeration {
                        enum priority;
                    }
                }                  //priority
                leaf COST_VALUE {
                    type int32;
                }                  //(0-255)
                leaf poll-interval {
                    type enumeration {
                        enum poll-interval;
                    }
                }                  //poll-interval
                leaf network {
                    type enumeration {
                        enum network;
                    }
                }                  //network
                leaf proactive-arp {
                    type enumeration {
                        enum proactive-arp;
                    }
                }                  //proactive-arp
                leaf router-info {
                    type enumeration {
                        enum router-info;
                    }
                }                  //router-info
                leaf summary-address {
                    type enumeration {
                        enum summary-address;
                    }
                }                  //summary-address
                leaf tag {
                    type enumeration {
                        enum tag;
                    }
                }                  //tag
                leaf ROUTER_TAG_VALUE {
                    type int32;
                }                  //(1-4294967295)
                leaf no-advertise {
                    type enumeration {
                        enum no-advertise;
                    }
                }                  //no-advertise
                leaf write-multiplier {
                    type enumeration {
                        enum write-multiplier;
                    }
                }                  //write-multiplier
                leaf MAXIMUM_NUMBER_OF_INTERFACE {
                    type int32;
                }                  //(1-100)
            }
            list AREA {
                key "PREFIX";
                leaf PREFIX {
                    type string; 
                } 
                leaf OSPF_AREA_ID_IN {
                    type union {
                        type inet:ipv4-address;
                        type int32;
                    }
                }                  //<A.B.C.D|(0-4294967295)>
                leaf authentication {
                    type enumeration {
                        enum authentication;
                    }
                }                  //authentication
                leaf authentication_message-digest {
                    type enumeration {
                        enum authentication_message-digest;
                    }
                }                  //message-digest
                leaf default-cost {
                    type enumeration {
                        enum default-cost;
                    }
                }                  //default-cost
                leaf STUB_ADVERTISED_DEFAULT_SUMMARY {
                    type int32;
                }                  //(0-16777215)
                leaf export-list {
                    type enumeration {
                        enum export-list;
                    }
                }                  //export-list
                leaf NAME_OF_THE_ACCESS-LIST {
                    type string;
                }                  //ACCESSLIST4_NAME
                leaf filter-list_prefix {
                    type enumeration {
                        enum filter-list_prefix;
                    }
                }                  //prefix
                leaf NAME_OF_AN_IP {
                    type string;
                }                  //PREFIXLIST_NAME
                leaf IN_OUT_BOUND {
                    type enumeration {
                        enum in;
                        enum out;
                    }
                }                  //<in|out> ['Filter networks sent to this area', 'Filter networks sent from this area']
                leaf import-list {
                    type enumeration {
                        enum import-list;
                    }
                }                  //import-list
                leaf nssa {
                    type enumeration {
                        enum nssa;
                    }
                }                  //nssa
                leaf NSSA_TRANSLATE_MODE {
                    type enumeration {
                        enum translate-candidate;
                        enum translate-never;
                        enum translate-always;
                    }
                }                  //<translate-candidate|translate-never|translate-always> ['Configure NSSA-ABR for translate election (default)', 'Configure NSSA-ABR to never translate', 'Configure NSSA-ABR to always translate']
                leaf nssa_no-summary {
                    type enumeration {
                        enum nssa_no-summary;
                    }
                }                  //no-summary
                leaf nssa_suppress-fa {
                    type enumeration {
                        enum nssa_suppress-fa;
                    }
                }                  //suppress-fa
                leaf range {
                    type enumeration {
                        enum range;
                    }
                }                  //range
                leaf IPV4_PREFIX {
                    type inet:ipv4-prefix;
                }                  //A.B.C.D/M
                leaf advertise {
                    type enumeration {
                        enum advertise;
                    }
                }                  //advertise
                leaf advertise_cost {
                    type enumeration {
                        enum advertise_cost;
                    }
                }                  //cost
                leaf ADVERTISED_METRIC_FOR_THIS {
                    type int32;
                }                  //(0-16777215)
                leaf not-advertise {
                    type enumeration {
                        enum not-advertise;
                    }
                }                  //not-advertise
                leaf cost {
                    type enumeration {
                        enum cost;
                    }
                }                  //cost
                leaf substitute {
                    type enumeration {
                        enum substitute;
                    }
                }                  //substitute
                leaf shortcut {
                    type enumeration {
                        enum shortcut;
                    }
                }                  //shortcut
                leaf SHORTCUT_MODE {
                    type enumeration {
                        enum default;
                        enum enable;
                        enum disable;
                    }
                }                  //<default|enable|disable> ['Set default shortcutting behavior', 'Enable shortcutting through the area', 'Disable shortcutting through the area']
                leaf stub {
                    type enumeration {
                        enum stub;
                    }
                }                  //stub
                leaf stub_no-summary {
                    type enumeration {
                        enum stub_no-summary;
                    }
                }                  //no-summary
                leaf virtual-link {
                    type enumeration {
                        enum virtual-link;
                    }
                }                  //virtual-link
                leaf ROUTER_ID_OF_THE {
                    type inet:ipv4-address;
                }                  //A.B.C.D
                leaf AUTHENTICATION_TYPE {
                    type enumeration {
                        enum message-digest;
                        enum null;
                    }
                }                  //<message-digest|null> ['Use message-digest authentication', 'Use null authentication']
                leaf message-digest-key {
                    type int32;
                }                  //(1-255)
                leaf md5 {
                    type string;
                }                  //KEY
                leaf authentication-key {
                    type string;
                }                  //AUTH_KEY
                leaf hello-interval {
                    type enumeration {
                        enum hello-interval;
                    }
                }                  //hello-interval
                leaf SECONDS {
                    type int32;
                }                  //(1-65535)
                leaf retransmit-interval {
                    type enumeration {
                        enum retransmit-interval;
                    }
                }                  //retransmit-interval
                leaf transmit-delay {
                    type enumeration {
                        enum transmit-delay;
                    }
                }                  //transmit-delay
                leaf dead-interval {
                    type enumeration {
                        enum dead-interval;
                    }
                }                  //dead-interval
            }
            list OSPF {
                key "PREFIX";
                leaf PREFIX {
                    type string; 
                } 
                leaf abr-type {
                    type enumeration {
                        enum abr-type;
                    }
                }                  //abr-type
                leaf ABR_TYPE {
                    type enumeration {
                        enum cisco;
                        enum ibm;
                        enum shortcut;
                        enum standard;
                    }
                }                  //<cisco|ibm|shortcut|standard> ['Alternative ABR, cisco implementation', 'Alternative ABR, IBM implementation', 'Shortcut ABR', 'Standard behavior (RFC2328)']
                leaf opaque-lsa {
                    type enumeration {
                        enum opaque-lsa;
                    }
                }                  //opaque-lsa
                leaf rfc1583compatibility {
                    type enumeration {
                        enum rfc1583compatibility;
                    }
                }                  //rfc1583compatibility
                leaf router-id {
                    type enumeration {
                        enum router-id;
                    }
                }                  //router-id
                leaf OSPF_ROUTER-ID_IN_IP {
                    type inet:ipv4-address;
                }                  //A.B.C.D
                leaf write-multiplier {
                    type enumeration {
                        enum write-multiplier;
                    }
                }                  //write-multiplier
                leaf MAXIMUM_NUMBER_OF_INTERFACE {
                    type int32;
                }                  //(1-100)
            }
            list AGGREGATION {
                key "PREFIX";
                leaf PREFIX {
                    type string; 
                } 
                leaf timer {
                    type enumeration {
                        enum timer;
                    }
                }                  //timer
                leaf TIMER_INTERVAL {
                    type int32;
                }                  //(5-1800)
            }
            list AUTO-COST {
                key "PREFIX";
                leaf PREFIX {
                    type string; 
                } 
                leaf reference-bandwidth {
                    type enumeration {
                        enum reference-bandwidth;
                    }
                }                  //reference-bandwidth
                leaf THE_REFERENCE_BANDWIDTH_IN {
                    type int32;
                }                  //(1-4294967)
            }
            list CAPABILITY {
                key "PREFIX";
                leaf PREFIX {
                    type string; 
                } 
                leaf opaque {
                    type enumeration {
                        enum opaque;
                    }
                }                  //opaque
            }
            list COMPATIBLE {
                key "PREFIX";
                leaf PREFIX {
                    type string; 
                } 
                leaf rfc1583 {
                    type enumeration {
                        enum rfc1583;
                    }
                }                  //rfc1583
            }
            list DEFAULT-METRIC {
                key "PREFIX";
                leaf PREFIX {
                    type string; 
                } 
                leaf DEFAULT_METRIC {
                    type int32;
                }                  //(0-16777214)
            }
            list DISTANCE {
                key "PREFIX";
                leaf PREFIX {
                    type string; 
                } 
                leaf OSPF_ADMINISTRATIVE_DISTANCE {
                    type int32;
                }                  //(1-255)
            }
            list DISTRIBUTE-LIST {
                key "PREFIX";
                leaf PREFIX {
                    type string; 
                } 
                leaf ACCESS-LIST_NAME {
                    type string;
                }                  //ACCESSLIST4_NAME
                leaf out {
                    type enumeration {
                        enum out;
                    }
                }                  //out
                leaf FRR_REDIST_HELP_STR_OSPFD {
                    type string;
                }                  //FRR_REDIST_STR_OSPFD
            }
            list LOG-ADJACENCY-CHANGES {
                key "PREFIX";
                leaf PREFIX {
                    type string; 
                } 
                leaf detail {
                    type enumeration {
                        enum detail;
                    }
                }                  //detail
            }
            list MAXIMUM-PATHS {
                key "PREFIX";
                leaf PREFIX {
                    type string; 
                } 
                leaf NUMBER_OF_PATHS {
                    type string;
                }                  //CMD_RANGE_STR
            }
            list MPLS-TE {
                key "PREFIX";
                leaf PREFIX {
                    type string; 
                } 
                leaf export {
                    type enumeration {
                        enum export;
                    }
                }                  //export
                leaf on {
                    type enumeration {
                        enum on;
                    }
                }                  //on
                leaf router-address {
                    type enumeration {
                        enum router-address;
                    }
                }                  //router-address
                leaf MPLS-TE_ROUTER_ADDRESS_IN {
                    type inet:ipv4-address;
                }                  //A.B.C.D
            }
            list NEIGHBOR {
                key "PREFIX";
                leaf PREFIX {
                    type string; 
                } 
                leaf NEIGHBOR_IP_ADDRESS {
                    type inet:ipv4-address;
                }                  //A.B.C.D
                leaf priority {
                    type enumeration {
                        enum priority;
                    }
                }                  //priority
                leaf COST_VALUE {
                    type int32;
                }                  //(0-255)
                leaf poll-interval {
                    type enumeration {
                        enum poll-interval;
                    }
                }                  //poll-interval
                leaf SECONDS {
                    type int32;
                }                  //(1-65535)
            }
            list NETWORK {
                key "PREFIX";
                leaf PREFIX {
                    type string; 
                } 
                leaf IPV4_PREFIX {
                    type inet:ipv4-prefix;
                }                  //A.B.C.D/M
                leaf area {
                    type enumeration {
                        enum area;
                    }
                }                  //area
                leaf OSPF_AREA_ID_IN {
                    type union {
                        type inet:ipv4-address;
                        type int32;
                    }
                }                  //<A.B.C.D|(0-4294967295)>
            }
            list PASSIVE-INTERFACE {
                key "PREFIX";
                leaf PREFIX {
                    type string; 
                } 
                leaf INTERFACE_NAME {
                    type string;
                }                  //IFNAME
                leaf IPV4_ADDRESS {
                    type inet:ipv4-address;
                }                  //A.B.C.D
                leaf default {
                    type enumeration {
                        enum default;
                    }
                }                  //default
            }
            list PCE {
                key "PREFIX";
                leaf PREFIX {
                    type string; 
                } 
                leaf address {
                    type enumeration {
                        enum address;
                    }
                }                  //address
                leaf PCE_ADDRESS_IN_IPV4 {
                    type inet:ipv4-address;
                }                  //A.B.C.D
                leaf flag {
                    type enumeration {
                        enum flag;
                    }
                }                  //flag
                leaf HEXADECIMAL_VALUE {
                    type string;
                }                  //BITPATTERN
                leaf scope {
                    type enumeration {
                        enum scope;
                    }
                }                  //scope
            }
            list PROACTIVE-ARP {
                key "PREFIX";
                leaf PREFIX {
                    type string; 
                } 
            }
            list REDISTRIBUTE {
                key "PREFIX";
                leaf PREFIX {
                    type string; 
                } 
                leaf ROUTE_SOURCE {
                    type enumeration {
                        enum ospf;
                        enum table;
                    }
                }                  //<ospf|table> ['Open Shortest Path First', 'Non-main Kernel Routing Table']
                leaf INSTANCE_IDTABLE_ID {
                    type int32;
                }                  //(1-65535)
                leaf metric {
                    type enumeration {
                        enum metric;
                    }
                }                  //metric
                leaf OSPF_DEFAULT_METRIC {
                    type int32;
                }                  //(0-16777214)
                leaf metric-type {
                    type enumeration {
                        enum metric-type;
                    }
                }                  //metric-type
                leaf SET_OSPF_EXTERNAL_TYPE {
                    type int32;
                }                  //(1-2)
                leaf route-map {
                    type enumeration {
                        enum route-map;
                    }
                }                  //route-map
                leaf POINTER_TO_ROUTE-MAP_ENTRIES {
                    type string;
                }                  //RMAP_NAME
                leaf FRR_REDIST_HELP_STR_OSPFD {
                    type string;
                }                  //FRR_REDIST_STR_OSPFD
            }
            list REFRESH {
                key "PREFIX";
                leaf PREFIX {
                    type string; 
                } 
                leaf timer {
                    type enumeration {
                        enum timer;
                    }
                }                  //timer
                leaf TIMER_VALUE_IN_SECONDS {
                    type int32;
                }                  //(10-1800)
            }
            list ROUTER-ID {
                key "PREFIX";
                leaf PREFIX {
                    type string; 
                } 
                leaf OSPF_ROUTER-ID_IN_IP {
                    type inet:ipv4-address;
                }                  //A.B.C.D
            }
            list ROUTER-INFO {
                key "PREFIX";
                leaf PREFIX {
                    type string; 
                } 
                leaf as {
                    type enumeration {
                        enum as;
                    }
                }                  //as
            }
            list SEGMENT-ROUTING {
                key "PREFIX";
                leaf PREFIX {
                    type string; 
                } 
                leaf global-block {
                    type enumeration {
                        enum global-block;
                    }
                }                  //global-block
                leaf LOWER-BOUND_RANGE_IN_DECIMAL {
                    type int32;
                }                  //(16-1048575)
                leaf UPPER-BOUND_RANGE_IN_DECIMAL {
                    type int32;
                }                  //(16-1048575)
                leaf local-block {
                    type enumeration {
                        enum local-block;
                    }
                }                  //local-block
                leaf node-msd {
                    type enumeration {
                        enum node-msd;
                    }
                }                  //node-msd
                leaf MAXIMUM_NUMBER_OF_LABEL {
                    type int32;
                }                  //(1-16)
                leaf on {
                    type enumeration {
                        enum on;
                    }
                }                  //on
                leaf prefix {
                    type enumeration {
                        enum prefix;
                    }
                }                  //prefix
                leaf IPV4_PREFIX {
                    type inet:ipv4-prefix;
                }                  //A.B.C.D/M
                leaf index {
                    type enumeration {
                        enum index;
                    }
                }                  //index
                leaf INDEX_VALUE_INSIDE_SRGB {
                    type int32;
                }                  //(0-65535)
                leaf no-php-flag {
                    type enumeration {
                        enum no-php-flag;
                    }
                }                  //no-php-flag
                leaf explicit-null {
                    type enumeration {
                        enum explicit-null;
                    }
                }                  //explicit-null
            }
            list SUMMARY-ADDRESS {
                key "PREFIX";
                leaf PREFIX {
                    type string; 
                } 
                leaf IPV4_PREFIX {
                    type inet:ipv4-prefix;
                }                  //A.B.C.D/M
                leaf tag {
                    type enumeration {
                        enum tag;
                    }
                }                  //tag
                leaf ROUTER_TAG_VALUE {
                    type int32;
                }                  //(1-4294967295)
                leaf no-advertise {
                    type enumeration {
                        enum no-advertise;
                    }
                }                  //no-advertise
            }
            list WRITE-MULTIPLIER {
                key "PREFIX";
                leaf PREFIX {
                    type string; 
                } 
                leaf MAXIMUM_NUMBER_OF_INTERFACE {
                    type int32;
                }                  //(1-100)
            }
            list NO_OSPF {
                key "PREFIX";
                leaf PREFIX {
                    type string; 
                } 
                leaf abr-type {
                    type enumeration {
                        enum abr-type;
                    }
                }                  //abr-type
                leaf ABR_TYPE {
                    type enumeration {
                        enum cisco;
                        enum ibm;
                        enum shortcut;
                        enum standard;
                    }
                }                  //<cisco|ibm|shortcut|standard> ['Alternative ABR, cisco implementation', 'Alternative ABR, IBM implementation', 'Shortcut ABR', 'Standard ABR']
                leaf opaque-lsa {
                    type enumeration {
                        enum opaque-lsa;
                    }
                }                  //opaque-lsa
                leaf rfc1583compatibility {
                    type enumeration {
                        enum rfc1583compatibility;
                    }
                }                  //rfc1583compatibility
                leaf write-multiplier {
                    type enumeration {
                        enum write-multiplier;
                    }
                }                  //write-multiplier
                leaf MAXIMUM_NUMBER_OF_INTERFACE {
                    type int32;
                }                  //(1-100)
            }
            list NO_AGGREGATION {
                key "PREFIX";
                leaf PREFIX {
                    type string; 
                } 
                leaf timer {
                    type enumeration {
                        enum timer;
                    }
                }                  //timer
            }
            list NO_CAPABILITY {
                key "PREFIX";
                leaf PREFIX {
                    type string; 
                } 
                leaf opaque {
                    type enumeration {
                        enum opaque;
                    }
                }                  //opaque
            }
            list NO_COMPATIBLE {
                key "PREFIX";
                leaf PREFIX {
                    type string; 
                } 
                leaf rfc1583 {
                    type enumeration {
                        enum rfc1583;
                    }
                }                  //rfc1583
            }
            list NO_DEFAULT-METRIC {
                key "PREFIX";
                leaf PREFIX {
                    type string; 
                } 
                leaf DEFAULT_METRIC {
                    type int32;
                }                  //(0-16777214)
            }
            list NO_DISTANCE {
                key "PREFIX";
                leaf PREFIX {
                    type string; 
                } 
                leaf OSPF_ADMINISTRATIVE_DISTANCE {
                    type int32;
                }                  //(1-255)
            }
            list NO_LOG-ADJACENCY-CHANGES {
                key "PREFIX";
                leaf PREFIX {
                    type string; 
                } 
                leaf detail {
                    type enumeration {
                        enum detail;
                    }
                }                  //detail
            }
            list NO_MPLS-TE {
                key "PREFIX";
                leaf PREFIX {
                    type string; 
                } 
                leaf on {
                    type enumeration {
                        enum on;
                    }
                }                  //on
                leaf export {
                    type enumeration {
                        enum export;
                    }
                }                  //export
                leaf inter-as {
                    type enumeration {
                        enum inter-as;
                    }
                }                  //inter-as
            }
            list NO_PASSIVE-INTERFACE {
                key "PREFIX";
                leaf PREFIX {
                    type string; 
                } 
                leaf INTERFACE_NAME {
                    type string;
                }                  //IFNAME
                leaf IPV4_ADDRESS {
                    type inet:ipv4-address;
                }                  //A.B.C.D
                leaf default {
                    type enumeration {
                        enum default;
                    }
                }                  //default
            }
            list NO_PCE {
                key "PREFIX";
                leaf PREFIX {
                    type string; 
                } 
                leaf flag {
                    type enumeration {
                        enum flag;
                    }
                }                  //flag
            }
            list NO_REDISTRIBUTE {
                key "PREFIX";
                leaf PREFIX {
                    type string; 
                } 
                leaf ROUTE_SOURCE {
                    type enumeration {
                        enum ospf;
                        enum table;
                    }
                }                  //<ospf|table> ['Open Shortest Path First', 'Non-main Kernel Routing Table']
                leaf INSTANCE_IDTABLE_ID {
                    type int32;
                }                  //(1-65535)
                leaf metric {
                    type enumeration {
                        enum metric;
                    }
                }                  //metric
                leaf OSPF_DEFAULT_METRIC {
                    type int32;
                }                  //(0-16777214)
                leaf metric-type {
                    type enumeration {
                        enum metric-type;
                    }
                }                  //metric-type
                leaf SET_OSPF_EXTERNAL_TYPE {
                    type int32;
                }                  //(1-2)
                leaf route-map {
                    type enumeration {
                        enum route-map;
                    }
                }                  //route-map
                leaf POINTER_TO_ROUTE-MAP_ENTRIES {
                    type string;
                }                  //RMAP_NAME
                leaf FRR_REDIST_HELP_STR_OSPFD {
                    type string;
                }                  //FRR_REDIST_STR_OSPFD
            }
            list NO_SEGMENT-ROUTING {
                key "PREFIX";
                leaf PREFIX {
                    type string; 
                } 
                leaf on {
                    type enumeration {
                        enum on;
                    }
                }                  //on
                leaf prefix {
                    type enumeration {
                        enum prefix;
                    }
                }                  //prefix
                leaf IPV4_PREFIX {
                    type inet:ipv4-prefix;
                }                  //A.B.C.D/M
                leaf index {
                    type enumeration {
                        enum index;
                    }
                }                  //index
                leaf INDEX_VALUE_INSIDE_SRGB {
                    type int32;
                }                  //(0-65535)
                leaf no-php-flag {
                    type enumeration {
                        enum no-php-flag;
                    }
                }                  //no-php-flag
                leaf explicit-null {
                    type enumeration {
                        enum explicit-null;
                    }
                }                  //explicit-null
            }
            list OSPF_SEND-EXTRA-DATA {
                key "PREFIX";
                leaf PREFIX {
                    type string; 
                } 
                leaf zebra {
                    type enumeration {
                        enum zebra;
                    }
                }                  //zebra
            }
            list DEFAULT-INFORMATION_ORIGINATE {
                key "PREFIX";
                leaf PREFIX {
                    type string; 
                } 
                leaf always {
                    type enumeration {
                        enum always;
                    }
                }                  //always
                leaf metric {
                    type enumeration {
                        enum metric;
                    }
                }                  //metric
                leaf OSPF_METRIC {
                    type int32;
                }                  //(0-16777214)
                leaf metric-type {
                    type enumeration {
                        enum metric-type;
                    }
                }                  //metric-type
                leaf SET_OSPF_EXTERNAL_TYPE {
                    type int32;
                }                  //(1-2)
                leaf route-map {
                    type enumeration {
                        enum route-map;
                    }
                }                  //route-map
                leaf POINTER_TO_ROUTE-MAP_ENTRIES {
                    type string;
                }                  //RMAP_NAME
            }
            list DISTANCE_OSPF {
                key "PREFIX";
                leaf PREFIX {
                    type string; 
                } 
                leaf intra-area {
                    type enumeration {
                        enum intra-area;
                    }
                }                  //intra-area
                leaf DISTANCE_FOR_INTRA-AREA_ROUTES {
                    type int32;
                }                  //(1-255)
                leaf inter-area {
                    type enumeration {
                        enum inter-area;
                    }
                }                  //inter-area
                leaf DISTANCE_FOR_INTER-AREA_ROUTES {
                    type int32;
                }                  //(1-255)
                leaf external {
                    type enumeration {
                        enum external;
                    }
                }                  //external
                leaf DISTANCE_FOR_EXTERNAL_ROUTES {
                    type int32;
                }                  //(1-255)
            }
            list FAST-REROUTE_TI-LFA {
                key "PREFIX";
                leaf PREFIX {
                    type string; 
                } 
                leaf node-protection {
                    type enumeration {
                        enum node-protection;
                    }
                }                  //node-protection
            }
            list GRACEFUL-RESTART_HELPER {
                key "PREFIX";
                leaf PREFIX {
                    type string; 
                } 
                leaf planned-only {
                    type enumeration {
                        enum planned-only;
                    }
                }                  //planned-only
                leaf strict-lsa-checking {
                    type enumeration {
                        enum strict-lsa-checking;
                    }
                }                  //strict-lsa-checking
                leaf supported-grace-time {
                    type enumeration {
                        enum supported-grace-time;
                    }
                }                  //supported-grace-time
                leaf GRACE_INTERVAL {
                    type int32;
                }                  //(10-1800)
            }
            list MAX-METRIC_ROUTER-LSA {
                key "PREFIX";
                leaf PREFIX {
                    type string; 
                } 
                leaf administrative {
                    type enumeration {
                        enum administrative;
                    }
                }                  //administrative
                leaf on-shutdown {
                    type enumeration {
                        enum on-shutdown;
                    }
                }                  //on-shutdown
                leaf TIME_TO_WAIT_TILL {
                    type int32;
                }                  //(5-100)
                leaf on-startup {
                    type enumeration {
                        enum on-startup;
                    }
                }                  //on-startup
                leaf TIME_TO_ADVERTISE_SELF {
                    type int32;
                }                  //(5-86400)
            }
            list MPLS-TE_INTER-AS {
                key "PREFIX";
                leaf PREFIX {
                    type string; 
                } 
                leaf area {
                    type enumeration {
                        enum area;
                    }
                }                  //area
                leaf OSPF_AREA_ID_IN {
                    type union {
                        type inet:ipv4-address;
                        type int32;
                    }
                }                  //<A.B.C.D|(0-4294967295)>
                leaf as {
                    type enumeration {
                        enum as;
                    }
                }                  //as
            }
            list PCE_DOMAIN {
                key "PREFIX";
                leaf PREFIX {
                    type string; 
                } 
                leaf as {
                    type enumeration {
                        enum as;
                    }
                }                  //as
                leaf AS_NUMBER_IN_DECIMAL {
                    type int32;
                }                  //(0-65535)
            }
            list PCE_NEIGHBOR {
                key "PREFIX";
                leaf PREFIX {
                    type string; 
                } 
                leaf as {
                    type enumeration {
                        enum as;
                    }
                }                  //as
                leaf AS_NUMBER_IN_DECIMAL {
                    type int32;
                }                  //(0-65535)
            }
            list ROUTER-INFO_AREA {
                key "PREFIX";
                leaf PREFIX {
                    type string; 
                } 
                leaf OSPF_AREA_ID_IN {
                    type inet:ipv4-address;
                }                  //A.B.C.D
            }
            list TIMERS_LSA {
                key "PREFIX";
                leaf PREFIX {
                    type string; 
                } 
                leaf min-arrival {
                    type enumeration {
                        enum min-arrival;
                    }
                }                  //min-arrival
                leaf DELAY_IN_MILLISECONDS {
                    type int32;
                }                  //(0-600000)
            }
            list TIMERS_THROTTLE {
                key "PREFIX";
                leaf PREFIX {
                    type string; 
                } 
                leaf spf {
                    type enumeration {
                        enum spf;
                    }
                }                  //spf
                leaf DELAY_FROM_FIRST_CHANGE {
                    type int32;
                }                  //(0-600000)
                leaf INITIAL_HOLD_TIME_BETWEEN {
                    type int32;
                }                  //(0-600000)
                leaf MAXIMUM_HOLD_TIME {
                    type int32;
                }                  //(0-600000)
            }
            list NO_OSPF_SEND-EXTRA-DATA {
                key "PREFIX";
                leaf PREFIX {
                    type string; 
                } 
                leaf zebra {
                    type enumeration {
                        enum zebra;
                    }
                }                  //zebra
            }
            list NO_OSPF_ROUTER-ID {
                key "PREFIX";
                leaf PREFIX {
                    type string; 
                } 
                leaf OSPF_ROUTER-ID_IN_IP {
                    type inet:ipv4-address;
                }                  //A.B.C.D
            }
            list NO_AUTO-COST_REFERENCE-BANDWIDTH {
                key "PREFIX";
                leaf PREFIX {
                    type string; 
                } 
                leaf THE_REFERENCE_BANDWIDTH_IN {
                    type int32;
                }                  //(1-4294967)
            }
            list NO_DEFAULT-INFORMATION_ORIGINATE {
                key "PREFIX";
                leaf PREFIX {
                    type string; 
                } 
                leaf always {
                    type enumeration {
                        enum always;
                    }
                }                  //always
                leaf metric {
                    type enumeration {
                        enum metric;
                    }
                }                  //metric
                leaf OSPF_METRIC {
                    type int32;
                }                  //(0-16777214)
                leaf metric-type {
                    type enumeration {
                        enum metric-type;
                    }
                }                  //metric-type
                leaf SET_OSPF_EXTERNAL_TYPE {
                    type int32;
                }                  //(1-2)
                leaf route-map {
                    type enumeration {
                        enum route-map;
                    }
                }                  //route-map
                leaf POINTER_TO_ROUTE-MAP_ENTRIES {
                    type string;
                }                  //RMAP_NAME
            }
            list NO_FAST-REROUTE_TI-LFA {
                key "PREFIX";
                leaf PREFIX {
                    type string; 
                } 
                leaf node-protection {
                    type enumeration {
                        enum node-protection;
                    }
                }                  //node-protection
            }
            list NO_GRACEFUL-RESTART_HELPER {
                key "PREFIX";
                leaf PREFIX {
                    type string; 
                } 
                leaf planned-only {
                    type enumeration {
                        enum planned-only;
                    }
                }                  //planned-only
                leaf strict-lsa-checking {
                    type enumeration {
                        enum strict-lsa-checking;
                    }
                }                  //strict-lsa-checking
                leaf supported-grace-time {
                    type enumeration {
                        enum supported-grace-time;
                    }
                }                  //supported-grace-time
                leaf GRACE_INTERVAL {
                    type int32;
                }                  //(10-1800)
            }
            list NO_MAX-METRIC_ROUTER-LSA {
                key "PREFIX";
                leaf PREFIX {
                    type string; 
                } 
                leaf administrative {
                    type enumeration {
                        enum administrative;
                    }
                }                  //administrative
            }
            list NO_PCE_ADDRESS {
                key "PREFIX";
                leaf PREFIX {
                    type string; 
                } 
                leaf PCE_ADDRESS_IN_IPV4 {
                    type inet:ipv4-address;
                }                  //A.B.C.D
            }
            list NO_PCE_DOMAIN {
                key "PREFIX";
                leaf PREFIX {
                    type string; 
                } 
                leaf as {
                    type enumeration {
                        enum as;
                    }
                }                  //as
                leaf AS_NUMBER_IN_DECIMAL {
                    type int32;
                }                  //(0-65535)
            }
            list NO_PCE_NEIGHBOR {
                key "PREFIX";
                leaf PREFIX {
                    type string; 
                } 
                leaf as {
                    type enumeration {
                        enum as;
                    }
                }                  //as
                leaf AS_NUMBER_IN_DECIMAL {
                    type int32;
                }                  //(0-65535)
            }
            list NO_PCE_SCOPE {
                key "PREFIX";
                leaf PREFIX {
                    type string; 
                } 
                leaf HEXADECIMAL_VALUE {
                    type string;
                }                  //BITPATTERN
            }
            list NO_REFRESH_TIMER {
                key "PREFIX";
                leaf PREFIX {
                    type string; 
                } 
                leaf TIMER_VALUE_IN_SECONDS {
                    type int32;
                }                  //(10-1800)
            }
            list NO_SEGMENT-ROUTING_GLOBAL-BLOCK {
                key "PREFIX";
                leaf PREFIX {
                    type string; 
                } 
                leaf LOWER-BOUND_RANGE_IN_DECIMAL {
                    type int32;
                }                  //(16-1048575)
                leaf UPPER-BOUND_RANGE_IN_DECIMAL {
                    type int32;
                }                  //(16-1048575)
                leaf local-block {
                    type enumeration {
                        enum local-block;
                    }
                }                  //local-block
            }
            list NO_SEGMENT-ROUTING_NODE-MSD {
                key "PREFIX";
                leaf PREFIX {
                    type string; 
                } 
                leaf MAXIMUM_NUMBER_OF_LABEL {
                    type int32;
                }                  //(1-16)
            }
            list GRACEFUL-RESTART_HELPER_ENABLE {
                key "PREFIX";
                leaf PREFIX {
                    type string; 
                } 
                leaf ADVERTISING_ROUTER-ID {
                    type inet:ipv4-address;
                }                  //A.B.C.D
            }
            list TIMERS_THROTTLE_LSA {
                key "PREFIX";
                leaf PREFIX {
                    type string; 
                } 
                leaf all {
                    type enumeration {
                        enum all;
                    }
                }                  //all
                leaf DELAY_BETWEEN_SENDING_LSAS {
                    type int32;
                }                  //(0-5000)
            }
            list NO_DISTANCE_OSPF_INTRA-AREA {
                key "PREFIX";
                leaf PREFIX {
                    type string; 
                } 
                leaf DISTANCE_FOR_INTRA-AREA_ROUTES {
                    type int32;
                }                  //(1-255)
            }
            list NO_DISTANCE_OSPF_INTER-AREA {
                key "PREFIX";
                leaf PREFIX {
                    type string; 
                } 
                leaf DISTANCE_FOR_INTER-AREA_ROUTES {
                    type int32;
                }                  //(1-255)
            }
            list NO_DISTANCE_OSPF_EXTERNAL {
                key "PREFIX";
                leaf PREFIX {
                    type string; 
                } 
                leaf DISTANCE_FOR_EXTERNAL_ROUTES {
                    type int32;
                }                  //(1-255)
            }
            list NO_GRACEFUL-RESTART_HELPER_ENABLE {
                key "PREFIX";
                leaf PREFIX {
                    type string; 
                } 
                leaf ADVERTISING_ROUTER-ID {
                    type inet:ipv4-address;
                }                  //A.B.C.D
            }
            list NO_MAX-METRIC_ROUTER-LSA_ON-SHUTDOWN {
                key "PREFIX";
                leaf PREFIX {
                    type string; 
                } 
                leaf TIME_TO_WAIT_TILL {
                    type int32;
                }                  //(5-100)
            }
            list NO_MAX-METRIC_ROUTER-LSA_ON-STARTUP {
                key "PREFIX";
                leaf PREFIX {
                    type string; 
                } 
                leaf TIME_TO_ADVERTISE_SELF {
                    type int32;
                }                  //(5-86400)
            }
            list NO_TIMERS_LSA_MIN-ARRIVAL {
                key "PREFIX";
                leaf PREFIX {
                    type string; 
                } 
                leaf DELAY_IN_MILLISECONDS {
                    type int32;
                }                  //(0-600000)
            }
            list NO_TIMERS_THROTTLE_SPF {
                key "PREFIX";
                leaf PREFIX {
                    type string; 
                } 
                leaf DELAY_FROM_FIRST_CHANGE {
                    type int32;
                }                  //(0-600000)
                leaf INITIAL_HOLD_TIME_BETWEEN {
                    type int32;
                }                  //(0-600000)
                leaf MAXIMUM_HOLD_TIME {
                    type int32;
                }                  //(0-600000)
            }
            list NO_TIMERS_THROTTLE_LSA_ALL {
                key "PREFIX";
                leaf PREFIX {
                    type string; 
                } 
                leaf DELAY_BETWEEN_SENDING_LSAS {
                    type int32;
                }                  //(0-5000)
            }
        }
        container OSPF6_NODE {
            list NO {
                key "PREFIX";
                leaf PREFIX {
                    type string; 
                } 
            }
            list OSPF6 {
                key "PREFIX";
                leaf PREFIX {
                    type string; 
                } 
            }
            list AGGREGATION {
                key "PREFIX";
                leaf PREFIX {
                    type string; 
                } 
            }
            list AREA {
                key "PREFIX";
                leaf PREFIX {
                    type string; 
                } 
            }
            list AUTO-COST {
                key "PREFIX";
                leaf PREFIX {
                    type string; 
                } 
            }
            list DISTANCE {
                key "PREFIX";
                leaf PREFIX {
                    type string; 
                } 
            }
            list INTERFACE {
                key "PREFIX";
                leaf PREFIX {
                    type string; 
                } 
            }
            list LOG-ADJACENCY-CHANGES {
                key "PREFIX";
                leaf PREFIX {
                    type string; 
                } 
            }
            list MAXIMUM-PATHS {
                key "PREFIX";
                leaf PREFIX {
                    type string; 
                } 
            }
            list REDISTRIBUTE {
                key "PREFIX";
                leaf PREFIX {
                    type string; 
                } 
            }
            list STUB-ROUTER {
                key "PREFIX";
                leaf PREFIX {
                    type string; 
                } 
            }
            list SUMMARY-ADDRESS {
                key "PREFIX";
                leaf PREFIX {
                    type string; 
                } 
            }
            list WRITE-MULTIPLIER {
                key "PREFIX";
                leaf PREFIX {
                    type string; 
                } 
            }
            list NO_DISTANCE {
                key "PREFIX";
                leaf PREFIX {
                    type string; 
                } 
            }
            list NO_LOG-ADJACENCY-CHANGES {
                key "PREFIX";
                leaf PREFIX {
                    type string; 
                } 
            }
            list NO_MAXIMUM-PATHS {
                key "PREFIX";
                leaf PREFIX {
                    type string; 
                } 
            }
            list NO_STUB-ROUTER {
                key "PREFIX";
                leaf PREFIX {
                    type string; 
                } 
            }
            list OSPF6_SEND-EXTRA-DATA {
                key "PREFIX";
                leaf PREFIX {
                    type string; 
                } 
            }
            list DEFAULT-INFORMATION_ORIGINATE {
                key "PREFIX";
                leaf PREFIX {
                    type string; 
                } 
            }
            list DISTANCE_OSPF6 {
                key "PREFIX";
                leaf PREFIX {
                    type string; 
                } 
            }
            list TIMERS_LSA {
                key "PREFIX";
                leaf PREFIX {
                    type string; 
                } 
            }
            list TIMERS_THROTTLE {
                key "PREFIX";
                leaf PREFIX {
                    type string; 
                } 
            }
            list NO_OSPF6_SEND-EXTRA-DATA {
                key "PREFIX";
                leaf PREFIX {
                    type string; 
                } 
            }
            list NO_OSPF6_ROUTER-ID {
                key "PREFIX";
                leaf PREFIX {
                    type string; 
                } 
            }
            list NO_AGGREGATION_TIMER {
                key "PREFIX";
                leaf PREFIX {
                    type string; 
                } 
            }
            list NO_AUTO-COST_REFERENCE-BANDWIDTH {
                key "PREFIX";
                leaf PREFIX {
                    type string; 
                } 
            }
            list NO_DEFAULT-INFORMATION_ORIGINATE {
                key "PREFIX";
                leaf PREFIX {
                    type string; 
                } 
            }
            list NO_DISTANCE_OSPF6_INTRA-AREA {
                key "PREFIX";
                leaf PREFIX {
                    type string; 
                } 
            }
            list NO_DISTANCE_OSPF6_INTER-AREA {
                key "PREFIX";
                leaf PREFIX {
                    type string; 
                } 
            }
            list NO_DISTANCE_OSPF6_EXTERNAL {
                key "PREFIX";
                leaf PREFIX {
                    type string; 
                } 
            }
            list NO_TIMERS_LSA_MIN-ARRIVAL {
                key "PREFIX";
                leaf PREFIX {
                    type string; 
                } 
            }
            list NO_TIMERS_THROTTLE_SPF {
                key "PREFIX";
                leaf PREFIX {
                    type string; 
                } 
            }
        }

    }
}
