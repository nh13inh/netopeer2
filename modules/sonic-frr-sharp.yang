module sonic-frr-sharp {
    namespace "http://github.com/sonic-net/frr/sonic-frr-sharp";
    prefix frr-sharp;
    yang-version 1.1;

    import ietf-inet-types {
        prefix inet;
    }

    organization
        "SONiC";

    contact
        "SONiC";

    description
        "SONIC frr-sharp FRR YANG";

    revision 2024-12-23 {
        description
            "Initial revision.";
    }
    container sonic-frr-sharp {

    }
}
