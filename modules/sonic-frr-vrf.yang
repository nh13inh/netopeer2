module sonic-frr-vrf {
    namespace "http://github.com/sonic-net/frr/sonic-frr-vrf";
    prefix frr-vrf;
    yang-version 1.1;

    import ietf-inet-types {
        prefix inet;
    }

    organization
        "SONiC";

    contact
        "SONiC";

    description
        "SONIC frr-vrf FRR YANG";

    revision 2024-12-23 {
        description
            "Initial revision.";
    }
    container sonic-frr-vrf {
        container VRF_NODE {
            list NO {
                key "PREFIX";
                leaf PREFIX {
                    type string; 
                } 
                leaf vni {
                    type enumeration {
                        enum vni;
                    }
                }                  //vni
                leaf VNI-ID {
                    type int32;
                }                  //(1-16777215)
                leaf prefix-routes-only {
                    type enumeration {
                        enum prefix-routes-only;
                    }
                }                  //prefix-routes-only
            }
            list IP {
                key "PREFIX";
                leaf PREFIX {
                    type string; 
                } 
                leaf route {
                    type enumeration {
                        enum route;
                    }
                }                  //route
                leaf IPV4_PREFIX {
                    type union {
                        type inet:ipv4-prefix;
                        type inet:ipv4-address;
                        type inet:ipv4-address;
                    }
                }                  //<A.B.C.D/M|A.B.C.D A.B.C.D>
                leaf IP_GATEWAY_ADDRESS {
                    type inet:ipv4-address;
                }                  //A.B.C.D
                leaf tag {
                    type enumeration {
                        enum tag;
                    }
                }                  //tag
                leaf TAG_VALUE {
                    type int32;
                }                  //(1-4294967295)
                leaf DISTANCE_VALUE_FOR_THIS {
                    type int32;
                }                  //(1-255)
                leaf label {
                    type enumeration {
                        enum label;
                    }
                }                  //label
                leaf ONE_OR_MORE_LABELS {
                    type string;
                }                  //WORD
                leaf table {
                    type enumeration {
                        enum table;
                    }
                }                  //table
                leaf THE_TABLE_NUMBER_TO {
                    type int32;
                }                  //(1-4294967295)
                leaf nexthop-vrf {
                    type enumeration {
                        enum nexthop-vrf;
                    }
                }                  //nexthop-vrf
                leaf THE_VRF_NAME {
                    type string;
                }                  //NAME
                leaf color {
                    type enumeration {
                        enum color;
                    }
                }                  //color
                leaf THE_SR-TE_COLOR_TO {
                    type int32;
                }                  //(1-4294967295)
                leaf bfd {
                    type enumeration {
                        enum bfd;
                    }
                }                  //bfd
                leaf bfd_multi-hop {
                    type enumeration {
                        enum bfd_multi-hop;
                    }
                }                  //multi-hop
                leaf bfd_source {
                    type enumeration {
                        enum bfd_source;
                    }
                }                  //source
                leaf USE_IPV4_SOURCE_FOR {
                    type inet:ipv4-address;
                }                  //A.B.C.D
                leaf bfd_profile {
                    type enumeration {
                        enum bfd_profile;
                    }
                }                  //profile
                leaf BFD_PROFILE_NAME {
                    type string;
                }                  //BFDPROF
                leaf IFNAME {
                    type union {
                        type string;
                        type enumeration {
                        enum Null0;
                        }
                    }
                }                  //<INTERFACE|Null0>
                leaf onlink {
                    type enumeration {
                        enum onlink;
                    }
                }                  //onlink
                leaf DROP_ACTION {
                    type enumeration {
                        enum reject;
                        enum blackhole;
                    }
                }                  //<reject|blackhole> ['Emit an ICMP unreachable when matched', 'Silently discard pkts when matched']
            }
            list IPV6 {
                key "PREFIX";
                leaf PREFIX {
                    type string; 
                } 
                leaf route {
                    type enumeration {
                        enum route;
                    }
                }                  //route
                leaf IPV6_DESTINATION_PREFIX_ {
                    type inet:ipv6-prefix;
                }                  //X:X::X:X/M
                leaf from {
                    type enumeration {
                        enum from;
                    }
                }                  //from
                leaf IPV6_SOURCE_PREFIX {
                    type inet:ipv6-prefix;
                }                  //X:X::X:X/M
                leaf IPV6_GATEWAY_ADDRESS {
                    type inet:ipv6-address;
                }                  //X:X::X:X
                leaf tag {
                    type enumeration {
                        enum tag;
                    }
                }                  //tag
                leaf TAG_VALUE {
                    type int32;
                }                  //(1-4294967295)
                leaf DISTANCE_VALUE_FOR_THIS {
                    type int32;
                }                  //(1-255)
                leaf label {
                    type enumeration {
                        enum label;
                    }
                }                  //label
                leaf ONE_OR_MORE_LABELS {
                    type string;
                }                  //WORD
                leaf table {
                    type enumeration {
                        enum table;
                    }
                }                  //table
                leaf THE_TABLE_NUMBER_TO {
                    type int32;
                }                  //(1-4294967295)
                leaf nexthop-vrf {
                    type enumeration {
                        enum nexthop-vrf;
                    }
                }                  //nexthop-vrf
                leaf THE_VRF_NAME {
                    type string;
                }                  //NAME
                leaf color {
                    type enumeration {
                        enum color;
                    }
                }                  //color
                leaf THE_SR-TE_COLOR_TO {
                    type int32;
                }                  //(1-4294967295)
                leaf bfd {
                    type enumeration {
                        enum bfd;
                    }
                }                  //bfd
                leaf bfd_multi-hop {
                    type enumeration {
                        enum bfd_multi-hop;
                    }
                }                  //multi-hop
                leaf bfd_source {
                    type enumeration {
                        enum bfd_source;
                    }
                }                  //source
                leaf USE_IPV4_SOURCE_FOR {
                    type inet:ipv6-address;
                }                  //X:X::X:X
                leaf bfd_profile {
                    type enumeration {
                        enum bfd_profile;
                    }
                }                  //profile
                leaf BFD_PROFILE_NAME {
                    type string;
                }                  //BFDPROF
                leaf IFNAME {
                    type union {
                        type string;
                        type enumeration {
                        enum Null0;
                        }
                    }
                }                  //<INTERFACE|Null0>
                leaf onlink {
                    type enumeration {
                        enum onlink;
                    }
                }                  //onlink
                leaf DROP_ACTION {
                    type enumeration {
                        enum reject;
                        enum blackhole;
                    }
                }                  //<reject|blackhole> ['Emit an ICMP unreachable when matched', 'Silently discard pkts when matched']
            }
            list EXIT-VRF {
                key "PREFIX";
                leaf PREFIX {
                    type string; 
                } 
            }
            list NETNS {
                key "PREFIX";
                leaf PREFIX {
                    type string; 
                } 
                leaf THE_FILE_NAME_IN {
                    type string;
                }                  //NAME
            }
            list VNI {
                key "PREFIX";
                leaf PREFIX {
                    type string; 
                } 
                leaf VNI-ID {
                    type int32;
                }                  //(1-16777215)
                leaf prefix-routes-only {
                    type enumeration {
                        enum prefix-routes-only;
                    }
                }                  //prefix-routes-only
            }
            list NO_IP {
                key "PREFIX";
                leaf PREFIX {
                    type string; 
                } 
                leaf route {
                    type enumeration {
                        enum route;
                    }
                }                  //route
                leaf IPV4_PREFIX {
                    type union {
                        type inet:ipv4-prefix;
                        type inet:ipv4-address;
                        type inet:ipv4-address;
                    }
                }                  //<A.B.C.D/M|A.B.C.D A.B.C.D>
                leaf IP_GATEWAY_ADDRESS {
                    type inet:ipv4-address;
                }                  //A.B.C.D
                leaf tag {
                    type enumeration {
                        enum tag;
                    }
                }                  //tag
                leaf TAG_VALUE {
                    type int32;
                }                  //(1-4294967295)
                leaf DISTANCE_VALUE_FOR_THIS {
                    type int32;
                }                  //(1-255)
                leaf label {
                    type enumeration {
                        enum label;
                    }
                }                  //label
                leaf ONE_OR_MORE_LABELS {
                    type string;
                }                  //WORD
                leaf table {
                    type enumeration {
                        enum table;
                    }
                }                  //table
                leaf THE_TABLE_NUMBER_TO {
                    type int32;
                }                  //(1-4294967295)
                leaf nexthop-vrf {
                    type enumeration {
                        enum nexthop-vrf;
                    }
                }                  //nexthop-vrf
                leaf THE_VRF_NAME {
                    type string;
                }                  //NAME
                leaf color {
                    type enumeration {
                        enum color;
                    }
                }                  //color
                leaf THE_SR-TE_COLOR_TO {
                    type int32;
                }                  //(1-4294967295)
                leaf bfd {
                    type enumeration {
                        enum bfd;
                    }
                }                  //bfd
                leaf bfd_multi-hop {
                    type enumeration {
                        enum bfd_multi-hop;
                    }
                }                  //multi-hop
                leaf bfd_source {
                    type enumeration {
                        enum bfd_source;
                    }
                }                  //source
                leaf USE_IPV4_SOURCE_FOR {
                    type inet:ipv4-address;
                }                  //A.B.C.D
                leaf bfd_profile {
                    type enumeration {
                        enum bfd_profile;
                    }
                }                  //profile
                leaf BFD_PROFILE_NAME {
                    type string;
                }                  //BFDPROF
                leaf IFNAME {
                    type union {
                        type string;
                        type enumeration {
                        enum Null0;
                        }
                    }
                }                  //<INTERFACE|Null0>
                leaf onlink {
                    type enumeration {
                        enum onlink;
                    }
                }                  //onlink
                leaf DROP_ACTION {
                    type enumeration {
                        enum reject;
                        enum blackhole;
                    }
                }                  //<reject|blackhole> ['Emit an ICMP unreachable when matched', 'Silently discard pkts when matched']
            }
            list NO_IPV6 {
                key "PREFIX";
                leaf PREFIX {
                    type string; 
                } 
                leaf route {
                    type enumeration {
                        enum route;
                    }
                }                  //route
                leaf IPV6_DESTINATION_PREFIX_ {
                    type inet:ipv6-prefix;
                }                  //X:X::X:X/M
                leaf from {
                    type enumeration {
                        enum from;
                    }
                }                  //from
                leaf IPV6_SOURCE_PREFIX {
                    type inet:ipv6-prefix;
                }                  //X:X::X:X/M
                leaf IPV6_GATEWAY_ADDRESS {
                    type inet:ipv6-address;
                }                  //X:X::X:X
                leaf tag {
                    type enumeration {
                        enum tag;
                    }
                }                  //tag
                leaf TAG_VALUE {
                    type int32;
                }                  //(1-4294967295)
                leaf DISTANCE_VALUE_FOR_THIS {
                    type int32;
                }                  //(1-255)
                leaf label {
                    type enumeration {
                        enum label;
                    }
                }                  //label
                leaf ONE_OR_MORE_LABELS {
                    type string;
                }                  //WORD
                leaf table {
                    type enumeration {
                        enum table;
                    }
                }                  //table
                leaf THE_TABLE_NUMBER_TO {
                    type int32;
                }                  //(1-4294967295)
                leaf nexthop-vrf {
                    type enumeration {
                        enum nexthop-vrf;
                    }
                }                  //nexthop-vrf
                leaf THE_VRF_NAME {
                    type string;
                }                  //NAME
                leaf color {
                    type enumeration {
                        enum color;
                    }
                }                  //color
                leaf THE_SR-TE_COLOR_TO {
                    type int32;
                }                  //(1-4294967295)
                leaf bfd {
                    type enumeration {
                        enum bfd;
                    }
                }                  //bfd
                leaf bfd_multi-hop {
                    type enumeration {
                        enum bfd_multi-hop;
                    }
                }                  //multi-hop
                leaf bfd_source {
                    type enumeration {
                        enum bfd_source;
                    }
                }                  //source
                leaf USE_IPV4_SOURCE_FOR {
                    type inet:ipv6-address;
                }                  //X:X::X:X
                leaf bfd_profile {
                    type enumeration {
                        enum bfd_profile;
                    }
                }                  //profile
                leaf BFD_PROFILE_NAME {
                    type string;
                }                  //BFDPROF
                leaf IFNAME {
                    type union {
                        type string;
                        type enumeration {
                        enum Null0;
                        }
                    }
                }                  //<INTERFACE|Null0>
                leaf onlink {
                    type enumeration {
                        enum onlink;
                    }
                }                  //onlink
                leaf DROP_ACTION {
                    type enumeration {
                        enum reject;
                        enum blackhole;
                    }
                }                  //<reject|blackhole> ['Emit an ICMP unreachable when matched', 'Silently discard pkts when matched']
            }
            list NO_NETNS {
                key "PREFIX";
                leaf PREFIX {
                    type string; 
                } 
                leaf THE_FILE_NAME_IN {
                    type string;
                }                  //NAME
            }
        }
        container BGP_VRF_POLICY_NODE {
            list EXIT-VRF-POLICY {
                key "PREFIX";
                leaf PREFIX {
                    type string; 
                } 
            }
            list EXPORT {
                key "PREFIX";
                leaf PREFIX {
                    type string; 
                } 
            }
            list LABEL {
                key "PREFIX";
                leaf PREFIX {
                    type string; 
                } 
            }
            list NEXTHOP {
                key "PREFIX";
                leaf PREFIX {
                    type string; 
                } 
            }
            list NO {
                key "PREFIX";
                leaf PREFIX {
                    type string; 
                } 
            }
            list RD {
                key "PREFIX";
                leaf PREFIX {
                    type string; 
                } 
            }
            list RT {
                key "PREFIX";
                leaf PREFIX {
                    type string; 
                } 
            }
            list NO_EXPORT {
                key "PREFIX";
                leaf PREFIX {
                    type string; 
                } 
            }
            list NO_EXPORT_ROUTE-MAP {
                key "PREFIX";
                leaf PREFIX {
                    type string; 
                } 
            }
        }

    }
}
