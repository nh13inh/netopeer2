module sonic-frr-bfd {
    namespace "http://github.com/sonic-net/frr/sonic-frr-bfd";
    prefix frr-bfd;
    yang-version 1.1;

    import ietf-inet-types {
        prefix inet;
    }

    organization
        "SONiC";

    contact
        "SONiC";

    description
        "SONIC frr-bfd FRR YANG";

    revision 2024-12-23 {
        description
            "Initial revision.";
    }
    container sonic-frr-bfd {
        container BFD_NODE {
            list NO {
                key "PREFIX";
                leaf PREFIX {
                    type string; 
                } 
                leaf peer {
                    type enumeration {
                        enum peer;
                    }
                }                  //peer
                leaf IP_ADDRESS {
                    type union {
                        type inet:ipv4-address;
                        type inet:ipv6-address;
                    }
                }                  //<A.B.C.D|X:X::X:X>
                leaf multihop {
                    type enumeration {
                        enum multihop;
                    }
                }                  //multihop
                leaf local-address {
                    type enumeration {
                        enum local-address;
                    }
                }                  //local-address
                leaf interface {
                    type enumeration {
                        enum interface;
                    }
                }                  //interface
                leaf CONFIGURE_LOCAL_INTERFACE_NAME {
                    type string;
                }                  //IFNAME
                leaf vrf {
                    type enumeration {
                        enum vrf;
                    }
                }                  //vrf
                leaf CONFIGURE_VRF_NAME {
                    type string;
                }                  //NAME
                leaf profile {
                    type enumeration {
                        enum profile;
                    }
                }                  //profile
                leaf BFD_PROFILE_NAME {
                    type string;
                }                  //BFDPROF
            }
            list PEER {
                key "PREFIX";
                leaf PREFIX {
                    type string; 
                } 
                leaf IP_ADDRESS {
                    type union {
                        type inet:ipv4-address;
                        type inet:ipv6-address;
                    }
                }                  //<A.B.C.D|X:X::X:X>
                leaf multihop {
                    type enumeration {
                        enum multihop;
                    }
                }                  //multihop
                leaf local-address {
                    type enumeration {
                        enum local-address;
                    }
                }                  //local-address
                leaf interface {
                    type enumeration {
                        enum interface;
                    }
                }                  //interface
                leaf CONFIGURE_INTERFACE_NAME_TO {
                    type string;
                }                  //IFNAME
                leaf vrf {
                    type enumeration {
                        enum vrf;
                    }
                }                  //vrf
                leaf CONFIGURE_VRF_NAME {
                    type string;
                }                  //NAME
            }
            list PROFILE {
                key "PREFIX";
                leaf PREFIX {
                    type string; 
                } 
                leaf BFD_PROFILE_NAME {
                    type string;
                }                  //BFDPROF
            }
            list QUIT {
                key "PREFIX";
                leaf PREFIX {
                    type string; 
                } 
            }
        }
        container BFD_PEER_NODE {
            list NO {
                key "PREFIX";
                leaf PREFIX {
                    type string; 
                } 
                leaf echo-mode {
                    type enumeration {
                        enum echo-mode;
                    }
                }                  //echo-mode
                leaf passive-mode {
                    type enumeration {
                        enum passive-mode;
                    }
                }                  //passive-mode
                leaf profile {
                    type enumeration {
                        enum profile;
                    }
                }                  //profile
                leaf BFD_PROFILE_NAME {
                    type string;
                }                  //BFDPROF
                leaf shutdown {
                    type enumeration {
                        enum shutdown;
                    }
                }                  //shutdown
            }
            list ECHO-MODE {
                key "PREFIX";
                leaf PREFIX {
                    type string; 
                } 
            }
            list MINIMUM-TTL {
                key "PREFIX";
                leaf PREFIX {
                    type string; 
                } 
                leaf MINIMUM_TTL_EXPECTED {
                    type int32;
                }                  //(1-254)
            }
            list PASSIVE-MODE {
                key "PREFIX";
                leaf PREFIX {
                    type string; 
                } 
            }
            list PROFILE {
                key "PREFIX";
                leaf PREFIX {
                    type string; 
                } 
                leaf BFD_PROFILE_NAME {
                    type string;
                }                  //BFDPROF
            }
            list SHUTDOWN {
                key "PREFIX";
                leaf PREFIX {
                    type string; 
                } 
            }
            list DETECT-MULTIPLIER {
                key "PREFIX";
                leaf PREFIX {
                    type string; 
                } 
                leaf CONFIGURE_PEER_DETECTION_MULTIPLIER {
                    type int32;
                }                  //(2-255)
            }
            list ECHO {
                key "PREFIX";
                leaf PREFIX {
                    type string; 
                } 
                leaf receive-interval {
                    type enumeration {
                        enum receive-interval;
                    }
                }                  //receive-interval
                leaf CONFIGURE_INTERVAL_VALUE_IN {
                    type int32;
                }                  //(10-60000)
                leaf disabled {
                    type enumeration {
                        enum disabled;
                    }
                }
                leaf transmit-interval {
                    type enumeration {
                        enum transmit-interval;
                    }
                }                  //transmit-interval
            }
            list ECHO-INTERVAL {
                key "PREFIX";
                leaf PREFIX {
                    type string; 
                } 
                leaf CONFIGURE_PEER_ECHO_RXTX {
                    type int32;
                }                  //(10-60000)
            }
            list RECEIVE-INTERVAL {
                key "PREFIX";
                leaf PREFIX {
                    type string; 
                } 
                leaf CONFIGURE_PEER_RECEIVE_INTERVAL {
                    type int32;
                }                  //(10-60000)
            }
            list TRANSMIT-INTERVAL {
                key "PREFIX";
                leaf PREFIX {
                    type string; 
                } 
                leaf CONFIGURE_PEER_TRANSMIT_INTERVAL {
                    type int32;
                }                  //(10-60000)
            }
            list NO_MINIMUM-TTL {
                key "PREFIX";
                leaf PREFIX {
                    type string; 
                } 
                leaf MINIMUM_TTL_EXPECTED {
                    type int32;
                }                  //(1-254)
            }
        }

    }
}
