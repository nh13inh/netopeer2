module sonic-frr-MACRO.h {
    namespace "http://github.com/sonic-net/frr/sonic-frr-MACRO.h";
    prefix frr-MACRO.h;
    yang-version 1.1;

    import ietf-inet-types {
        prefix inet;
    }

    organization
        "SONiC";

    contact
        "SONiC";

    description
        "SONIC frr-MACRO.h FRR YANG";

    revision 2024-12-23 {
        description
            "Initial revision.";
    }
    container sonic-frr-MACRO.h {

    }
}
