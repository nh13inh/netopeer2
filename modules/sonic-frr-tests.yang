module sonic-frr-tests {
    namespace "http://github.com/sonic-net/frr/sonic-frr-tests";
    prefix frr-tests;
    yang-version 1.1;

    import ietf-inet-types {
        prefix inet;
    }

    organization
        "SONiC";

    contact
        "SONiC";

    description
        "SONIC frr-tests FRR YANG";

    revision 2024-12-23 {
        description
            "Initial revision.";
    }
    container sonic-frr-tests {

    }
}
