module sonic-frr-watchfrr {
    namespace "http://github.com/sonic-net/frr/sonic-frr-watchfrr";
    prefix frr-watchfrr;
    yang-version 1.1;

    import ietf-inet-types {
        prefix inet;
    }

    organization
        "SONiC";

    contact
        "SONiC";

    description
        "SONIC frr-watchfrr FRR YANG";

    revision 2024-12-23 {
        description
            "Initial revision.";
    }
    container sonic-frr-watchfrr {

    }
}
