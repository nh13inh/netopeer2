module sonic-frr-vtysh {
    namespace "http://github.com/sonic-net/frr/sonic-frr-vtysh";
    prefix frr-vtysh;
    yang-version 1.1;

    import ietf-inet-types {
        prefix inet;
    }

    organization
        "SONiC";

    contact
        "SONiC";

    description
        "SONIC frr-vtysh FRR YANG";

    revision 2024-12-23 {
        description
            "Initial revision.";
    }
    container sonic-frr-vtysh {

    }
}
