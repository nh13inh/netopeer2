module sonic-frr-static {
    namespace "http://github.com/sonic-net/frr/sonic-frr-static";
    prefix frr-static;
    yang-version 1.1;

    import ietf-inet-types {
        prefix inet;
    }

    organization
        "SONiC";

    contact
        "SONiC";

    description
        "SONIC frr-static FRR YANG";

    revision 2024-12-23 {
        description
            "Initial revision.";
    }
    container sonic-frr-static {

    }
}
