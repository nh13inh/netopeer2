module sonic-frr-view {
    namespace "http://github.com/sonic-net/frr/sonic-frr-view";
    prefix frr-view;
    yang-version 1.1;

    import ietf-inet-types {
        prefix inet;
    }

    organization
        "SONiC";

    contact
        "SONiC";

    description
        "SONIC frr-view FRR YANG";

    revision 2024-12-23 {
        description
            "Initial revision.";
    }
    container sonic-frr-view {
        container VIEW_NODE {
            container destination {
                leaf none {
                    type enumeration {
                        enum none;
                    }
                }                  //none
            }
            list ENABLE {
                key "PREFIX";
                leaf PREFIX {
                    type string; 
                } 
            }
            container end {
            }
            container exit {
            }
            container find {
                leaf-list SEARCH_PATTERN {
                    type string;
                }                  //REGEX...
            }
            container list {
                leaf permutations {
                    type enumeration {
                        enum permutations;
                    }
                }                  //permutations
            }
            container mtrace {
                leaf MULTICAST_TRACE_ROUTE_TO {
                    type string;
                }                  //WORD
                leaf MULTICAST_TRACE_ROUTE_FOR {
                    type string;
                }                  //WORD
            }
            container output {
                leaf file {
                    type enumeration {
                        enum file;
                    }
                }                  //file
                leaf PATH_TO_DUMP_OUTPUT {
                    type string;
                }                  //FILE
            }
            container ping {
                leaf PING_DESTINATION_ADDRESS_OR {
                    type string;
                }                  //WORD
                leaf ip {
                    type enumeration {
                        enum ip;
                    }
                }                  //ip
                leaf ipv6 {
                    type enumeration {
                        enum ipv6;
                    }
                }                  //ipv6
            }
            container quit {
            }
            container show {
                leaf daemons {
                    type enumeration {
                        enum daemons;
                    }
                }                  //daemons
                leaf error {
                    type enumeration {
                        enum error;
                    }
                }                  //error
                leaf ERROR_CODE_TO_GET {
                    type int32;
                }                  //(1-4294967296)
                leaf all {
                    type enumeration {
                        enum all;
                    }
                }
                leaf json {
                    type enumeration {
                        enum json;
                    }
                }                  //json
                leaf frr {
                    type enumeration {
                        enum frr;
                    }
                }                  //frr
                leaf history {
                    type enumeration {
                        enum history;
                    }
                }                  //history
                leaf modules {
                    type enumeration {
                        enum modules;
                    }
                }                  //modules
                leaf motd {
                    type enumeration {
                        enum motd;
                    }
                }                  //motd
                leaf version {
                    type enumeration {
                        enum version;
                    }
                }                  //version
                leaf watchfrr {
                    type enumeration {
                        enum watchfrr;
                    }
                }                  //watchfrr
                leaf route-map-unused {
                    type enumeration {
                        enum route-map-unused;
                    }
                }                  //route-map-unused
                leaf startup-config {
                    type enumeration {
                        enum startup-config;
                    }
                }                  //startup-config
            }
            container traceroute {
                leaf TRACE_ROUTE_TO_DESTINATION {
                    type string;
                }                  //WORD
                leaf ip {
                    type enumeration {
                        enum ip;
                    }
                }                  //ip
                leaf ipv6 {
                    type enumeration {
                        enum ipv6;
                    }
                }                  //ipv6
            }
            container write {
                leaf STORAGE_TYPE {
                    type enumeration {
                        enum memory;
                        enum file;
                    }
                }                  //<memory|file> ['Write configuration to the file (same as write file)', 'Write configuration to the file (same as write memory)']
                leaf integrated {
                    type enumeration {
                        enum integrated;
                    }
                }                  //integrated
                leaf CONFIG_WRITE_TARGET {
                    type enumeration {
                        enum file;
                        enum memory;
                    }
                }                  //<file|memory> ['Write to configuration file', 'Write configuration currently in memory']
            }
            container debug {
                leaf memstats-at-exit {
                    type enumeration {
                        enum memstats-at-exit;
                    }
                }                  //memstats-at-exit
                leaf unique-id {
                    type enumeration {
                        enum unique-id;
                    }
                }                  //unique-id
                leaf LOG_MESSAGE_UNIQUE_ID {
                    type string;
                }                  //UID
                leaf backtrace {
                    type enumeration {
                        enum backtrace;
                    }
                }                  //backtrace
                leaf babel {
                    type enumeration {
                        enum babel;
                    }
                }                  //babel
                leaf LOGGING_MESSAGE_TYPE {
                    type enumeration {
                        enum common;
                        enum kernel;
                        enum filter;
                        enum timeout;
                        enum interface;
                        enum route;
                        enum all;
                    }
                }                  //<common|kernel|filter|timeout|interface|route|all> ['Common messages (default)', 'Kernel messages', 'Filter messages', 'Timeout messages', 'Interface messages', 'Route messages', 'All messages']
                leaf mtrace {
                    type enumeration {
                        enum mtrace;
                    }
                }                  //mtrace
                leaf nhrp {
                    type enumeration {
                        enum nhrp;
                    }
                }                  //nhrp
                leaf LOG_CATEGORY {
                    type enumeration {
                        enum all;
                        enum common;
                        enum event;
                        enum interface;
                        enum kernel;
                        enum route;
                        enum vici;
                    }
                }                  //<all|common|event|interface|kernel|route|vici> ['All messages', 'Common messages (default)', 'Event manager messages', 'Interface messages', 'Kernel messages', 'Route messages', 'VICI messages']
                leaf spf-delay-ietf {
                    type enumeration {
                        enum spf-delay-ietf;
                    }
                }                  //spf-delay-ietf
                leaf ssmpingd {
                    type enumeration {
                        enum ssmpingd;
                    }
                }                  //ssmpingd
            }
            container watchfrr {
                leaf ignore {
                    type enumeration {
                        enum ignore;
                    }
                }                  //ignore
                leaf THE_DAEMON_TO_IGNORE {
                    type string;
                }                  //DAEMON
            }
            container add {
                leaf vrf {
                    type enumeration {
                        enum vrf;
                    }
                }                  //vrf
                leaf VRF_NAME {
                    type string;
                }                  //NAME
                leaf prefix {
                    type enumeration {
                        enum prefix;
                    }
                }                  //prefix
                leaf IPV4_PREFIX {
                    type union {
                        type inet:ipv4-prefix;
                        type inet:ipv6-prefix;
                    }
                }                  //<A.B.C.D/M|X:X::X:X/M>
                leaf rd {
                    type enumeration {
                        enum rd;
                    }
                }                  //rd
                leaf BGP_IDENTIFIER {
                    type string;
                }                  //ASN:NN_OR_IP-ADDRESS
                leaf label {
                    type enumeration {
                        enum label;
                    }
                }                  //label
                leaf LABEL_VALUE {
                    type int32;
                }                  //(0-1048575)
                leaf preference {
                    type enumeration {
                        enum preference;
                    }
                }                  //preference
                leaf LOCAL_PREFERENCE {
                    type int32;
                }                  //(0-4294967295)
            }
            container clear {
                leaf vrf {
                    type enumeration {
                        enum vrf;
                    }
                }                  //vrf
                leaf VRF_NAME {
                    type string;
                }                  //NAME
                leaf prefix {
                    type enumeration {
                        enum prefix;
                    }
                }                  //prefix
                leaf IPV4_PREFIX {
                    type union {
                        type inet:ipv4-prefix;
                        type inet:ipv6-prefix;
                    }
                }                  //<A.B.C.D/M|X:X::X:X/M>
                leaf rd {
                    type enumeration {
                        enum rd;
                    }
                }                  //rd
                leaf BGP_IDENTIFIER {
                    type string;
                }                  //ASN:NN_OR_IP-ADDRESS
                leaf all {
                    type enumeration {
                        enum all;
                    }
                }                  //all
            }
            container configure {
                leaf terminal {
                    type enumeration {
                        enum terminal;
                    }
                }                  //terminal
                leaf exclusive {
                    type enumeration {
                        enum exclusive;
                    }
                }                  //exclusive
                leaf private {
                    type enumeration {
                        enum private;
                    }
                }                  //private
            }
            container copy {
                leaf CONFIGURATION_FILE_TO_READ {
                    type string;
                }                  //FILENAME
                leaf running-config {
                    type enumeration {
                        enum running-config;
                    }
                }                  //running-config
            }
            container disable {
            }
            container no_destination {
                leaf none {
                    type enumeration {
                        enum none;
                    }
                }                  //none
            }
            container no_terminal {
                leaf length {
                    type enumeration {
                        enum length;
                    }
                }                  //length
                leaf NUMBER_OF_LINES_ON {
                    type int32;
                }                  //(0-4294967295)
            }
            container no_match {
                leaf interface {
                    type enumeration {
                        enum interface;
                    }
                }                  //interface
                leaf INTERFACE_NAME {
                    type string;
                }                  //WORD
                leaf metric {
                    type enumeration {
                        enum metric;
                    }
                }                  //metric
                leaf METRIC_VALUE {
                    type int32;
                }                  //(0-4294967295)
                leaf tag {
                    type enumeration {
                        enum tag;
                    }
                }                  //tag
            }
            container no_set {
                leaf metric {
                    type enumeration {
                        enum metric;
                    }
                }                  //metric
                leaf METRIC_VALUE {
                    type int32;
                }                  //((0-4294967295)|
                leaf CHOICE_CASE {
                    type enumeration {
                        enum +/-metric;
                        enum );
                    }
                }                  //<+/-metric|)> ['Add or subtract metric']
                leaf tag {
                    type enumeration {
                        enum tag;
                    }
                }                  //tag
                leaf TAG_VALUE {
                    type int32;
                }                  //(0-65535)
            }
            container no_debug {
                leaf memstats-at-exit {
                    type enumeration {
                        enum memstats-at-exit;
                    }
                }                  //memstats-at-exit
                leaf unique-id {
                    type enumeration {
                        enum unique-id;
                    }
                }                  //unique-id
                leaf LOG_MESSAGE_UNIQUE_ID {
                    type string;
                }                  //UID
                leaf backtrace {
                    type enumeration {
                        enum backtrace;
                    }
                }                  //backtrace
                leaf babel {
                    type enumeration {
                        enum babel;
                    }
                }                  //babel
                leaf LOGGING_MESSAGE_TYPE {
                    type enumeration {
                        enum common;
                        enum kernel;
                        enum filter;
                        enum timeout;
                        enum interface;
                        enum route;
                        enum all;
                    }
                }                  //<common|kernel|filter|timeout|interface|route|all> ['Common messages (default)', 'Kernel messages', 'Filter messages', 'Timeout messages', 'Interface messages', 'Route messages', 'All messages']
                leaf mtrace {
                    type enumeration {
                        enum mtrace;
                    }
                }                  //mtrace
                leaf nhrp {
                    type enumeration {
                        enum nhrp;
                    }
                }                  //nhrp
                leaf LOG_CATEGORY {
                    type enumeration {
                        enum all;
                        enum common;
                        enum event;
                        enum interface;
                        enum kernel;
                        enum route;
                        enum vici;
                    }
                }                  //<all|common|event|interface|kernel|route|vici> ['All messages', 'Common messages (default)', 'Event manager messages', 'Interface messages', 'Kernel messages', 'Route messages', 'VICI messages']
                leaf spf-delay-ietf {
                    type enumeration {
                        enum spf-delay-ietf;
                    }
                }                  //spf-delay-ietf
                leaf ssmpingd {
                    type enumeration {
                        enum ssmpingd;
                    }
                }                  //ssmpingd
            }
            container no_watchfrr {
                leaf ignore {
                    type enumeration {
                        enum ignore;
                    }
                }                  //ignore
                leaf THE_DAEMON_TO_IGNORE {
                    type string;
                }                  //DAEMON
            }
            container no_sharp {
                leaf interface {
                    type enumeration {
                        enum interface;
                    }
                }                  //interface
                leaf INTERFACE_NAME {
                    type string;
                }                  //IFNAME
                leaf protodown {
                    type enumeration {
                        enum protodown;
                    }
                }                  //protodown
            }
            container terminal_length {
                leaf NUMBER_OF_LINES_ON {
                    type int32;
                }                  //(0-4294967295)
            }
            container terminal_monitor {
                leaf DAEMONS_LIST {
                    type enumeration {
                        enum babeld;
                        enum bgpd;
                        enum fabricd;
                        enum ldpd;
                        enum ospfd;
                        enum pbrd;
                        enum pimd;
                        enum ripngd;
                        enum vrrpd;
                        enum bfdd;
                        enum eigrpd;
                        enum isisd;
                        enum nhrpd;
                        enum ospf6d;
                        enum pathd;
                        enum pim6d;
                        enum ripd;
                        enum staticd;
                        enum zebra;
                    }
                }                  //<babeld|bgpd|fabricd|ldpd|ospfd|pbrd|pimd|ripngd|vrrpd|bfdd|eigrpd|isisd|nhrpd|ospf6d|pathd|pim6d|ripd|staticd|zebra> ['For the babeld daemon', 'For the bgpd daemon', 'For the fabricd daemon', 'For the ldpd daemon', 'For the ospfd daemon', 'For the pbrd daemon', 'For the pimd daemon', 'For the ripngd daemon', 'For the vrrpd daemon', 'For the bfdd daemon', 'For the eigrpd daemon', 'For the isisd daemon', 'For the nhrpd daemon', 'For the ospf6d daemon', 'For the pathd daemon', 'For the pim6d daemom', 'For the ripd daemon', 'For the staticd daemon', 'For the zebra daemon']
            }
            container terminal_no {
                leaf length {
                    type enumeration {
                        enum length;
                    }
                }                  //length
            }
            container show_ip {
                leaf forwarding {
                    type enumeration {
                        enum forwarding;
                    }
                }                  //forwarding
                leaf neigh {
                    type enumeration {
                        enum neigh;
                    }
                }                  //neigh
            }
            container show_ipv6 {
                leaf forwarding {
                    type enumeration {
                        enum forwarding;
                    }
                }                  //forwarding
            }
            container show_json {
                leaf nexthop-group {
                    type enumeration {
                        enum nexthop-group;
                    }
                }                  //nexthop-group
            }
            container show_bgp {
                leaf ADDRESS_FAMILY_TYPE {
                    type enumeration {
                        enum vpnv4;
                        enum vpnv6;
                    }
                }                  //<vpnv4|vpnv6> ['Address Family', 'Address Family']
                leaf all {
                    type enumeration {
                        enum all;
                    }
                }                  //all
                leaf IPV4_PREFIX {
                    type union {
                        type inet:ipv4-address;
                        type inet:ipv4-prefix;
                    }
                }                  //<A.B.C.D|A.B.C.D/M>
                leaf json {
                    type enumeration {
                        enum json;
                    }
                }                  //json
                leaf tags {
                    type enumeration {
                        enum tags;
                    }
                }                  //tags
                leaf rd {
                    type enumeration {
                        enum rd;
                    }
                }                  //rd
                leaf BGP_IDENTIFIER {
                    type string;
                }                  //ASN:NN_OR_IP-ADDRESS:NN
                leaf neighbors {
                    type enumeration {
                        enum neighbors;
                    }
                }                  //neighbors
                leaf NEIGHBOR_TO_DISPLAY_INFORMATION {
                    type inet:ipv4-address;
                }                  //A.B.C.D
                leaf advertised-routes {
                    type enumeration {
                        enum advertised-routes;
                    }
                }                  //advertised-routes
                leaf advertised-routes_json {
                    type enumeration {
                        enum advertised-routes_json;
                    }
                }                  //json
                leaf routes {
                    type enumeration {
                        enum routes;
                    }
                }                  //routes
                leaf routes_json {
                    type enumeration {
                        enum routes_json;
                    }
                }                  //json
                leaf all_neighbors {
                    type enumeration {
                        enum all_neighbors;
                    }
                }                  //all_neighbors
                leaf IP_ADDRESS {
                    type union {
                        type inet:ipv4-address;
                        type inet:ipv6-address;
                        type string;
                    }
                }                  //<A.B.C.D|X:X::X:X|WORD>
                leaf prefix-counts {
                    type enumeration {
                        enum prefix-counts;
                    }
                }                  //prefix-counts
                leaf prefix-counts_json {
                    type enumeration {
                        enum prefix-counts_json;
                    }
                }                  //json
                leaf ADDRESS_FAMILY_MODIFIER {
                    type enumeration {
                        enum unicast;
                        enum multicast;
                        enum vpn;
                    }
                }                  //<unicast|multicast|vpn> ['Address Family modifier', 'Address Family modifier', 'Address Family modifier']
                leaf paths {
                    type enumeration {
                        enum paths;
                    }
                }                  //paths
                leaf REDISTRIBUTE_IP {
                    type enumeration {
                        enum ipv4;
                        enum ipv6;
                    }
                }                  //<ipv4|ipv6> ['Address Family', 'Address Family']
                leaf route-leak {
                    type enumeration {
                        enum route-leak;
                    }
                }                  //route-leak
                leaf route-leak_json {
                    type enumeration {
                        enum route-leak_json;
                    }
                }                  //json
                leaf all_community-list {
                    type enumeration {
                        enum all_community-list;
                    }
                }                  //community-list
                leaf COMMUNITY-LIST_NAME {
                    type union {
                        type int32;
                        type string;
                    }
                }                  //<(1-500)|COMMUNITY_LIST_NAME>
                leaf exact-match {
                    type enumeration {
                        enum exact-match;
                    }
                }                  //exact-match
                leaf exact-match_wide {
                    type enumeration {
                        enum exact-match_wide;
                    }
                }                  //wide
                leaf json_detail {
                    type enumeration {
                        enum json_detail;
                    }
                }                  //detail
                leaf wide {
                    type enumeration {
                        enum wide;
                    }
                }                  //wide
                leaf exact-match_json {
                    type enumeration {
                        enum exact-match_json;
                    }
                }                  //exact-match_json
                leaf exact-match_json_detail {
                    type enumeration {
                        enum exact-match_json_detail;
                    }
                }                  //detail
                leaf all_filter-list {
                    type enumeration {
                        enum all_filter-list;
                    }
                }                  //filter-list
                leaf REGULAR_EXPRESSION_ACCESS_LIST {
                    type string;
                }                  //AS_PATH_FILTER_NAME
                leaf all_prefix-list {
                    type enumeration {
                        enum all_prefix-list;
                    }
                }                  //prefix-list
                leaf PREFIX-LIST_NAME {
                    type string;
                }                  //WORD
                leaf all_access-list {
                    type enumeration {
                        enum all_access-list;
                    }
                }                  //access-list
                leaf ACCESS-LIST_NAME {
                    type string;
                }                  //ACCESSLIST_NAME
                leaf all_route-map {
                    type enumeration {
                        enum all_route-map;
                    }
                }                  //route-map
                leaf A_ROUTE-MAP_TO_MATCH {
                    type string;
                }                  //RMAP_NAME
                leaf all_rpki {
                    type enumeration {
                        enum all_rpki;
                    }
                }                  //rpki
                leaf CHOICE_CASE {
                    type enumeration {
                        enum invalid;
                        enum valid;
                        enum notfound;
                    }
                }                  //<invalid|valid|notfound> ['A valid path as determined by rpki', 'A invalid path as determined by rpki', 'A path that has no rpki data']
                leaf all_version {
                    type enumeration {
                        enum all_version;
                    }
                }                  //version
                leaf VERSION_NUMBER_AND_ABOVE {
                    type int32;
                }                  //(1-4294967295)
                leaf all_alias {
                    type enumeration {
                        enum all_alias;
                    }
                }                  //alias
                leaf BGP_COMMUNITY_ALIAS {
                    type string;
                }                  //ALIAS_NAME
                leaf all_wide {
                    type enumeration {
                        enum all_wide;
                    }
                }                  //wide
                leaf cidr-only {
                    type enumeration {
                        enum cidr-only;
                    }
                }                  //cidr-only
                leaf cidr-only_wide {
                    type enumeration {
                        enum cidr-only_wide;
                    }
                }                  //wide
                leaf dampening {
                    type enumeration {
                        enum dampening;
                    }
                }                  //dampening
                leaf community {
                    type enumeration {
                        enum community;
                    }
                }                  //community
                leaf community_wide {
                    type enumeration {
                        enum community_wide;
                    }
                }                  //wide
                leaf community-list {
                    type enumeration {
                        enum community-list;
                    }
                }                  //community-list
                leaf filter-list {
                    type enumeration {
                        enum filter-list;
                    }
                }                  //filter-list
                leaf prefix-list {
                    type enumeration {
                        enum prefix-list;
                    }
                }                  //prefix-list
                leaf access-list {
                    type enumeration {
                        enum access-list;
                    }
                }                  //access-list
                leaf route-map {
                    type enumeration {
                        enum route-map;
                    }
                }                  //route-map
                leaf rpki {
                    type enumeration {
                        enum rpki;
                    }
                }                  //rpki
                leaf version {
                    type enumeration {
                        enum version;
                    }
                }                  //version
                leaf alias {
                    type enumeration {
                        enum alias;
                    }
                }                  //alias
                leaf longer-prefixes {
                    type enumeration {
                        enum longer-prefixes;
                    }
                }                  //longer-prefixes
                leaf longer-prefixes_wide {
                    type enumeration {
                        enum longer-prefixes_wide;
                    }
                }                  //wide
                leaf longer-prefixes_json {
                    type enumeration {
                        enum longer-prefixes_json;
                    }
                }                  //longer-prefixes_json
                leaf longer-prefixes_json_detail {
                    type enumeration {
                        enum longer-prefixes_json_detail;
                    }
                }                  //detail
                leaf IPV6_PREFIX {
                    type inet:ipv6-prefix;
                }                  //X:X::X:X/M
                leaf detail-routes {
                    type enumeration {
                        enum detail-routes;
                    }
                }                  //detail-routes
                leaf detail-routes_wide {
                    type enumeration {
                        enum detail-routes_wide;
                    }
                }                  //wide
                leaf BGP_NEIGHBOR_ROUTE_DIRECTION {
                    type enumeration {
                        enum advertised-routes;
                        enum received-routes;
                        enum filtered-routes;
                    }
                }                  //<advertised-routes|received-routes|filtered-routes> ['Display the routes advertised to a BGP neighbor', 'Display the received routes from neighbor', 'Display the filtered routes received from neighbor']
                leaf detail {
                    type enumeration {
                        enum detail;
                    }
                }                  //detail
                leaf detail_json {
                    type enumeration {
                        enum detail_json;
                    }
                }                  //json
                leaf detail_wide {
                    type enumeration {
                        enum detail_wide;
                    }
                }                  //wide
                leaf BGP_NEIGHBOR_ROUTE_STATS {
                    type enumeration {
                        enum flap-statistics;
                        enum dampened-routes;
                        enum routes;
                    }
                }                  //<flap-statistics|dampened-routes|routes> ['Display flap statistics of the routes learned from neighbor', 'Display the dampened routes received from neighbor', 'Display routes learned from neighbor']
                leaf bestpath-routes {
                    type enumeration {
                        enum bestpath-routes;
                    }
                }                  //bestpath-routes
                leaf bestpath-routes_json {
                    type enumeration {
                        enum bestpath-routes_json;
                    }
                }                  //json
                leaf bestpath-routes_wide {
                    type enumeration {
                        enum bestpath-routes_wide;
                    }
                }                  //wide
                leaf graceful-restart {
                    type enumeration {
                        enum graceful-restart;
                    }
                }                  //graceful-restart
                leaf graceful-restart_json {
                    type enumeration {
                        enum graceful-restart_json;
                    }
                }                  //json
                leaf received_prefix-filter {
                    type enumeration {
                        enum received_prefix-filter;
                    }
                }                  //received_prefix-filter
                leaf received_prefix-filter_json {
                    type enumeration {
                        enum received_prefix-filter_json;
                    }
                }                  //json
                leaf neighbors_json {
                    type enumeration {
                        enum neighbors_json;
                    }
                }                  //json
                leaf summary {
                    type enumeration {
                        enum summary;
                    }
                }                  //summary
                leaf summary_neighbor {
                    type enumeration {
                        enum summary_neighbor;
                    }
                }                  //neighbor
                leaf terse {
                    type enumeration {
                        enum terse;
                    }
                }                  //terse
                leaf terse_json {
                    type enumeration {
                        enum terse_json;
                    }
                }                  //json
                leaf wide_json {
                    type enumeration {
                        enum wide_json;
                    }
                }                  //json
                leaf terse_wide {
                    type enumeration {
                        enum terse_wide;
                    }
                }                  //terse_wide
                leaf terse_wide_json {
                    type enumeration {
                        enum terse_wide_json;
                    }
                }                  //json
                leaf summary_remote-as {
                    type enumeration {
                        enum summary_remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
                leaf summary_json {
                    type enumeration {
                        enum summary_json;
                    }
                }                  //json
                leaf large-community {
                    type enumeration {
                        enum large-community;
                    }
                }                  //large-community
                leaf LARGE_COMMUNITY {
                    type string;
                }                  //AA:BB:CC
                leaf large-community_json {
                    type enumeration {
                        enum large-community_json;
                    }
                }                  //json
                leaf large-community-list {
                    type enumeration {
                        enum large-community-list;
                    }
                }                  //large-community-list
                leaf LARGE-COMMUNITY-LIST_NUMBER {
                    type union {
                        type int32;
                        type string;
                    }
                }                  //<(1-500)|LCOMMUNITY_LIST_NAME>
                leaf regexp {
                    type enumeration {
                        enum regexp;
                    }
                }                  //regexp
                leaf REGULAR_EXPRESSION {
                    type string;
                }                  //REGEX
                leaf statistics {
                    type enumeration {
                        enum statistics;
                    }
                }                  //statistics
                leaf statistics_json {
                    type enumeration {
                        enum statistics_json;
                    }
                }                  //json
                leaf update-groups {
                    type enumeration {
                        enum update-groups;
                    }
                }                  //update-groups
                leaf update-groups_json {
                    type enumeration {
                        enum update-groups_json;
                    }
                }                  //json
                leaf BGP_PATH_SELECTION {
                    type enumeration {
                        enum bestpath;
                        enum multipath;
                    }
                }                  //<bestpath|multipath> ['Display only the bestpath', 'Display only multipaths']
                leaf RPKI_VALIDATION_STATE {
                    type enumeration {
                        enum valid;
                        enum invalid;
                        enum notfound;
                    }
                }                  //<valid|invalid|notfound> ['A valid path as determined by rpki', 'A invalid path as determined by rpki', 'A path that has no rpki data']
                leaf unicast {
                    type enumeration {
                        enum unicast;
                    }
                }                  //unicast
                leaf unicast_community-list {
                    type enumeration {
                        enum unicast_community-list;
                    }
                }                  //community-list
                leaf unicast_filter-list {
                    type enumeration {
                        enum unicast_filter-list;
                    }
                }                  //filter-list
                leaf unicast_prefix-list {
                    type enumeration {
                        enum unicast_prefix-list;
                    }
                }                  //prefix-list
                leaf unicast_access-list {
                    type enumeration {
                        enum unicast_access-list;
                    }
                }                  //access-list
                leaf unicast_route-map {
                    type enumeration {
                        enum unicast_route-map;
                    }
                }                  //route-map
                leaf unicast_rpki {
                    type enumeration {
                        enum unicast_rpki;
                    }
                }                  //rpki
                leaf unicast_version {
                    type enumeration {
                        enum unicast_version;
                    }
                }                  //version
                leaf unicast_alias {
                    type enumeration {
                        enum unicast_alias;
                    }
                }                  //alias
                leaf unicast_wide {
                    type enumeration {
                        enum unicast_wide;
                    }
                }                  //wide
                leaf unicast_neighbors {
                    type enumeration {
                        enum unicast_neighbors;
                    }
                }                  //neighbors
                leaf unicast_large-community-list {
                    type enumeration {
                        enum unicast_large-community-list;
                    }
                }                  //large-community-list
                leaf unicast_regexp {
                    type enumeration {
                        enum unicast_regexp;
                    }
                }                  //regexp
                leaf flowspec {
                    type enumeration {
                        enum flowspec;
                    }
                }                  //flowspec
                leaf flowspec_community-list {
                    type enumeration {
                        enum flowspec_community-list;
                    }
                }                  //community-list
                leaf flowspec_filter-list {
                    type enumeration {
                        enum flowspec_filter-list;
                    }
                }                  //filter-list
                leaf flowspec_prefix-list {
                    type enumeration {
                        enum flowspec_prefix-list;
                    }
                }                  //prefix-list
                leaf flowspec_access-list {
                    type enumeration {
                        enum flowspec_access-list;
                    }
                }                  //access-list
                leaf flowspec_route-map {
                    type enumeration {
                        enum flowspec_route-map;
                    }
                }                  //route-map
                leaf flowspec_rpki {
                    type enumeration {
                        enum flowspec_rpki;
                    }
                }                  //rpki
                leaf flowspec_version {
                    type enumeration {
                        enum flowspec_version;
                    }
                }                  //version
                leaf flowspec_alias {
                    type enumeration {
                        enum flowspec_alias;
                    }
                }                  //alias
                leaf flowspec_wide {
                    type enumeration {
                        enum flowspec_wide;
                    }
                }                  //wide
                leaf flowspec_neighbors {
                    type enumeration {
                        enum flowspec_neighbors;
                    }
                }                  //neighbors
                leaf flowspec_large-community-list {
                    type enumeration {
                        enum flowspec_large-community-list;
                    }
                }                  //large-community-list
                leaf flowspec_regexp {
                    type enumeration {
                        enum flowspec_regexp;
                    }
                }                  //regexp
                leaf vpn {
                    type enumeration {
                        enum vpn;
                    }
                }                  //vpn
                leaf vpn_community-list {
                    type enumeration {
                        enum vpn_community-list;
                    }
                }                  //community-list
                leaf vpn_filter-list {
                    type enumeration {
                        enum vpn_filter-list;
                    }
                }                  //filter-list
                leaf vpn_prefix-list {
                    type enumeration {
                        enum vpn_prefix-list;
                    }
                }                  //prefix-list
                leaf vpn_access-list {
                    type enumeration {
                        enum vpn_access-list;
                    }
                }                  //access-list
                leaf vpn_route-map {
                    type enumeration {
                        enum vpn_route-map;
                    }
                }                  //route-map
                leaf vpn_rpki {
                    type enumeration {
                        enum vpn_rpki;
                    }
                }                  //rpki
                leaf vpn_version {
                    type enumeration {
                        enum vpn_version;
                    }
                }                  //version
                leaf vpn_alias {
                    type enumeration {
                        enum vpn_alias;
                    }
                }                  //alias
                leaf vpn_wide {
                    type enumeration {
                        enum vpn_wide;
                    }
                }                  //wide
                leaf vpn_neighbors {
                    type enumeration {
                        enum vpn_neighbors;
                    }
                }                  //neighbors
                leaf vpn_large-community-list {
                    type enumeration {
                        enum vpn_large-community-list;
                    }
                }                  //large-community-list
                leaf vpn_regexp {
                    type enumeration {
                        enum vpn_regexp;
                    }
                }                  //regexp
                leaf vpn_rd {
                    type enumeration {
                        enum vpn_rd;
                    }
                }                  //rd
                leaf all_cidr-only {
                    type enumeration {
                        enum all_cidr-only;
                    }
                }                  //all_cidr-only
                leaf all_cidr-only_wide {
                    type enumeration {
                        enum all_cidr-only_wide;
                    }
                }                  //wide
                leaf all_dampening {
                    type enumeration {
                        enum all_dampening;
                    }
                }                  //all_dampening
                leaf all_community {
                    type enumeration {
                        enum all_community;
                    }
                }                  //all_community
                leaf all_community_wide {
                    type enumeration {
                        enum all_community_wide;
                    }
                }                  //wide
                leaf all_detail-routes {
                    type enumeration {
                        enum all_detail-routes;
                    }
                }                  //all_detail-routes
                leaf all_detail-routes_wide {
                    type enumeration {
                        enum all_detail-routes_wide;
                    }
                }                  //wide
                leaf all_json {
                    type enumeration {
                        enum all_json;
                    }
                }                  //all_json
                leaf all_json_detail {
                    type enumeration {
                        enum all_json_detail;
                    }
                }                  //detail
                leaf all_summary {
                    type enumeration {
                        enum all_summary;
                    }
                }                  //all_summary
                leaf all_summary_neighbor {
                    type enumeration {
                        enum all_summary_neighbor;
                    }
                }                  //neighbor
                leaf all_summary_remote-as {
                    type enumeration {
                        enum all_summary_remote-as;
                    }
                }                  //remote-as
                leaf all_summary_json {
                    type enumeration {
                        enum all_summary_json;
                    }
                }                  //json
                leaf cidr-only_json {
                    type enumeration {
                        enum cidr-only_json;
                    }
                }                  //cidr-only_json
                leaf cidr-only_json_detail {
                    type enumeration {
                        enum cidr-only_json_detail;
                    }
                }                  //detail
                leaf dampening_parameters {
                    type enumeration {
                        enum dampening_parameters;
                    }
                }                  //dampening_parameters
                leaf dampening_parameters_json {
                    type enumeration {
                        enum dampening_parameters_json;
                    }
                }                  //json
                leaf community_local-AS {
                    type enumeration {
                        enum community_local-AS;
                    }
                }                  //community_local-AS
                leaf community_local-AS_wide {
                    type enumeration {
                        enum community_local-AS_wide;
                    }
                }                  //wide
                leaf community_no-advertise {
                    type enumeration {
                        enum community_no-advertise;
                    }
                }                  //community_no-advertise
                leaf community_no-advertise_wide {
                    type enumeration {
                        enum community_no-advertise_wide;
                    }
                }                  //wide
                leaf community_no-export {
                    type enumeration {
                        enum community_no-export;
                    }
                }                  //community_no-export
                leaf community_no-export_wide {
                    type enumeration {
                        enum community_no-export_wide;
                    }
                }                  //wide
                leaf community_graceful-shutdown {
                    type enumeration {
                        enum community_graceful-shutdown;
                    }
                }                  //community_graceful-shutdown
                leaf community_graceful-shutdown_wide {
                    type enumeration {
                        enum community_graceful-shutdown_wide;
                    }
                }                  //wide
                leaf community_no-peer {
                    type enumeration {
                        enum community_no-peer;
                    }
                }                  //community_no-peer
                leaf community_no-peer_wide {
                    type enumeration {
                        enum community_no-peer_wide;
                    }
                }                  //wide
                leaf community_blackhole {
                    type enumeration {
                        enum community_blackhole;
                    }
                }                  //community_blackhole
                leaf community_blackhole_wide {
                    type enumeration {
                        enum community_blackhole_wide;
                    }
                }                  //wide
                leaf community_llgr-stale {
                    type enumeration {
                        enum community_llgr-stale;
                    }
                }                  //community_llgr-stale
                leaf community_llgr-stale_wide {
                    type enumeration {
                        enum community_llgr-stale_wide;
                    }
                }                  //wide
                leaf community_no-llgr {
                    type enumeration {
                        enum community_no-llgr;
                    }
                }                  //community_no-llgr
                leaf community_no-llgr_wide {
                    type enumeration {
                        enum community_no-llgr_wide;
                    }
                }                  //wide
                leaf community_accept-own {
                    type enumeration {
                        enum community_accept-own;
                    }
                }                  //community_accept-own
                leaf community_accept-own_wide {
                    type enumeration {
                        enum community_accept-own_wide;
                    }
                }                  //wide
                leaf community_accept-own-nexthop {
                    type enumeration {
                        enum community_accept-own-nexthop;
                    }
                }                  //community_accept-own-nexthop
                leaf community_accept-own-nexthop_wide {
                    type enumeration {
                        enum community_accept-own-nexthop_wide;
                    }
                }                  //wide
                leaf community_route-filter-v6 {
                    type enumeration {
                        enum community_route-filter-v6;
                    }
                }                  //community_route-filter-v6
                leaf community_route-filter-v6_wide {
                    type enumeration {
                        enum community_route-filter-v6_wide;
                    }
                }                  //wide
                leaf community_route-filter-v4 {
                    type enumeration {
                        enum community_route-filter-v4;
                    }
                }                  //community_route-filter-v4
                leaf community_route-filter-v4_wide {
                    type enumeration {
                        enum community_route-filter-v4_wide;
                    }
                }                  //wide
                leaf community_route-filter-translated-v6 {
                    type enumeration {
                        enum community_route-filter-translated-v6;
                    }
                }                  //community_route-filter-translated-v6
                leaf community_route-filter-translated-v6_wide {
                    type enumeration {
                        enum community_route-filter-translated-v6_wide;
                    }
                }                  //wide
                leaf community_route-filter-translated-v4 {
                    type enumeration {
                        enum community_route-filter-translated-v4;
                    }
                }                  //community_route-filter-translated-v4
                leaf community_route-filter-translated-v4_wide {
                    type enumeration {
                        enum community_route-filter-translated-v4_wide;
                    }
                }                  //wide
                leaf community_exact-match {
                    type enumeration {
                        enum community_exact-match;
                    }
                }                  //community_exact-match
                leaf community_exact-match_wide {
                    type enumeration {
                        enum community_exact-match_wide;
                    }
                }                  //wide
                leaf community_json {
                    type enumeration {
                        enum community_json;
                    }
                }                  //community_json
                leaf community_json_detail {
                    type enumeration {
                        enum community_json_detail;
                    }
                }                  //detail
                leaf detail-routes_json {
                    type enumeration {
                        enum detail-routes_json;
                    }
                }                  //detail-routes_json
                leaf detail-routes_json_detail {
                    type enumeration {
                        enum detail-routes_json_detail;
                    }
                }                  //detail
                leaf summary_established {
                    type enumeration {
                        enum summary_established;
                    }
                }                  //summary_established
                leaf summary_established_neighbor {
                    type enumeration {
                        enum summary_established_neighbor;
                    }
                }                  //neighbor
                leaf summary_established_remote-as {
                    type enumeration {
                        enum summary_established_remote-as;
                    }
                }                  //remote-as
                leaf summary_established_json {
                    type enumeration {
                        enum summary_established_json;
                    }
                }                  //json
                leaf summary_failed {
                    type enumeration {
                        enum summary_failed;
                    }
                }                  //summary_failed
                leaf summary_failed_neighbor {
                    type enumeration {
                        enum summary_failed_neighbor;
                    }
                }                  //neighbor
                leaf summary_failed_remote-as {
                    type enumeration {
                        enum summary_failed_remote-as;
                    }
                }                  //remote-as
                leaf summary_failed_json {
                    type enumeration {
                        enum summary_failed_json;
                    }
                }                  //json
                leaf summary_terse {
                    type enumeration {
                        enum summary_terse;
                    }
                }                  //summary_terse
                leaf summary_terse_json {
                    type enumeration {
                        enum summary_terse_json;
                    }
                }                  //json
                leaf summary_wide {
                    type enumeration {
                        enum summary_wide;
                    }
                }                  //summary_wide
                leaf summary_wide_json {
                    type enumeration {
                        enum summary_wide_json;
                    }
                }                  //json
                leaf all_cidr-only_json {
                    type enumeration {
                        enum all_cidr-only_json;
                    }
                }                  //all_cidr-only_json
                leaf all_cidr-only_json_detail {
                    type enumeration {
                        enum all_cidr-only_json_detail;
                    }
                }                  //detail
                leaf all_dampening_parameters {
                    type enumeration {
                        enum all_dampening_parameters;
                    }
                }                  //all_dampening_parameters
                leaf all_dampening_parameters_json {
                    type enumeration {
                        enum all_dampening_parameters_json;
                    }
                }                  //json
                leaf all_community_local-AS {
                    type enumeration {
                        enum all_community_local-AS;
                    }
                }                  //all_community_local-AS
                leaf all_community_local-AS_wide {
                    type enumeration {
                        enum all_community_local-AS_wide;
                    }
                }                  //wide
                leaf all_community_no-advertise {
                    type enumeration {
                        enum all_community_no-advertise;
                    }
                }                  //all_community_no-advertise
                leaf all_community_no-advertise_wide {
                    type enumeration {
                        enum all_community_no-advertise_wide;
                    }
                }                  //wide
                leaf all_community_no-export {
                    type enumeration {
                        enum all_community_no-export;
                    }
                }                  //all_community_no-export
                leaf all_community_no-export_wide {
                    type enumeration {
                        enum all_community_no-export_wide;
                    }
                }                  //wide
                leaf all_community_graceful-shutdown {
                    type enumeration {
                        enum all_community_graceful-shutdown;
                    }
                }                  //all_community_graceful-shutdown
                leaf all_community_graceful-shutdown_wide {
                    type enumeration {
                        enum all_community_graceful-shutdown_wide;
                    }
                }                  //wide
                leaf all_community_no-peer {
                    type enumeration {
                        enum all_community_no-peer;
                    }
                }                  //all_community_no-peer
                leaf all_community_no-peer_wide {
                    type enumeration {
                        enum all_community_no-peer_wide;
                    }
                }                  //wide
                leaf all_community_blackhole {
                    type enumeration {
                        enum all_community_blackhole;
                    }
                }                  //all_community_blackhole
                leaf all_community_blackhole_wide {
                    type enumeration {
                        enum all_community_blackhole_wide;
                    }
                }                  //wide
                leaf all_community_llgr-stale {
                    type enumeration {
                        enum all_community_llgr-stale;
                    }
                }                  //all_community_llgr-stale
                leaf all_community_llgr-stale_wide {
                    type enumeration {
                        enum all_community_llgr-stale_wide;
                    }
                }                  //wide
                leaf all_community_no-llgr {
                    type enumeration {
                        enum all_community_no-llgr;
                    }
                }                  //all_community_no-llgr
                leaf all_community_no-llgr_wide {
                    type enumeration {
                        enum all_community_no-llgr_wide;
                    }
                }                  //wide
                leaf all_community_accept-own {
                    type enumeration {
                        enum all_community_accept-own;
                    }
                }                  //all_community_accept-own
                leaf all_community_accept-own_wide {
                    type enumeration {
                        enum all_community_accept-own_wide;
                    }
                }                  //wide
                leaf all_community_accept-own-nexthop {
                    type enumeration {
                        enum all_community_accept-own-nexthop;
                    }
                }                  //all_community_accept-own-nexthop
                leaf all_community_accept-own-nexthop_wide {
                    type enumeration {
                        enum all_community_accept-own-nexthop_wide;
                    }
                }                  //wide
                leaf all_community_route-filter-v6 {
                    type enumeration {
                        enum all_community_route-filter-v6;
                    }
                }                  //all_community_route-filter-v6
                leaf all_community_route-filter-v6_wide {
                    type enumeration {
                        enum all_community_route-filter-v6_wide;
                    }
                }                  //wide
                leaf all_community_route-filter-v4 {
                    type enumeration {
                        enum all_community_route-filter-v4;
                    }
                }                  //all_community_route-filter-v4
                leaf all_community_route-filter-v4_wide {
                    type enumeration {
                        enum all_community_route-filter-v4_wide;
                    }
                }                  //wide
                leaf all_community_route-filter-translated-v6 {
                    type enumeration {
                        enum all_community_route-filter-translated-v6;
                    }
                }                  //all_community_route-filter-translated-v6
                leaf all_community_route-filter-translated-v6_wide {
                    type enumeration {
                        enum all_community_route-filter-translated-v6_wide;
                    }
                }                  //wide
                leaf all_community_route-filter-translated-v4 {
                    type enumeration {
                        enum all_community_route-filter-translated-v4;
                    }
                }                  //all_community_route-filter-translated-v4
                leaf all_community_route-filter-translated-v4_wide {
                    type enumeration {
                        enum all_community_route-filter-translated-v4_wide;
                    }
                }                  //wide
                leaf all_community_exact-match {
                    type enumeration {
                        enum all_community_exact-match;
                    }
                }                  //all_community_exact-match
                leaf all_community_exact-match_wide {
                    type enumeration {
                        enum all_community_exact-match_wide;
                    }
                }                  //wide
                leaf all_community_json {
                    type enumeration {
                        enum all_community_json;
                    }
                }                  //all_community_json
                leaf all_community_json_detail {
                    type enumeration {
                        enum all_community_json_detail;
                    }
                }                  //detail
                leaf all_detail-routes_json {
                    type enumeration {
                        enum all_detail-routes_json;
                    }
                }                  //all_detail-routes_json
                leaf all_detail-routes_json_detail {
                    type enumeration {
                        enum all_detail-routes_json_detail;
                    }
                }                  //detail
                leaf all_summary_established {
                    type enumeration {
                        enum all_summary_established;
                    }
                }                  //all_summary_established
                leaf all_summary_established_neighbor {
                    type enumeration {
                        enum all_summary_established_neighbor;
                    }
                }                  //neighbor
                leaf all_summary_established_remote-as {
                    type enumeration {
                        enum all_summary_established_remote-as;
                    }
                }                  //remote-as
                leaf all_summary_established_json {
                    type enumeration {
                        enum all_summary_established_json;
                    }
                }                  //json
                leaf all_summary_failed {
                    type enumeration {
                        enum all_summary_failed;
                    }
                }                  //all_summary_failed
                leaf all_summary_failed_neighbor {
                    type enumeration {
                        enum all_summary_failed_neighbor;
                    }
                }                  //neighbor
                leaf all_summary_failed_remote-as {
                    type enumeration {
                        enum all_summary_failed_remote-as;
                    }
                }                  //remote-as
                leaf all_summary_failed_json {
                    type enumeration {
                        enum all_summary_failed_json;
                    }
                }                  //json
                leaf all_summary_terse {
                    type enumeration {
                        enum all_summary_terse;
                    }
                }                  //all_summary_terse
                leaf all_summary_terse_json {
                    type enumeration {
                        enum all_summary_terse_json;
                    }
                }                  //json
                leaf all_summary_wide {
                    type enumeration {
                        enum all_summary_wide;
                    }
                }                  //all_summary_wide
                leaf all_summary_wide_json {
                    type enumeration {
                        enum all_summary_wide_json;
                    }
                }                  //json
                leaf community_local-AS_exact-match {
                    type enumeration {
                        enum community_local-AS_exact-match;
                    }
                }                  //community_local-AS_exact-match
                leaf community_local-AS_exact-match_wide {
                    type enumeration {
                        enum community_local-AS_exact-match_wide;
                    }
                }                  //wide
                leaf community_local-AS_json {
                    type enumeration {
                        enum community_local-AS_json;
                    }
                }                  //community_local-AS_json
                leaf community_local-AS_json_detail {
                    type enumeration {
                        enum community_local-AS_json_detail;
                    }
                }                  //detail
                leaf community_no-advertise_exact-match {
                    type enumeration {
                        enum community_no-advertise_exact-match;
                    }
                }                  //community_no-advertise_exact-match
                leaf community_no-advertise_exact-match_wide {
                    type enumeration {
                        enum community_no-advertise_exact-match_wide;
                    }
                }                  //wide
                leaf community_no-advertise_json {
                    type enumeration {
                        enum community_no-advertise_json;
                    }
                }                  //community_no-advertise_json
                leaf community_no-advertise_json_detail {
                    type enumeration {
                        enum community_no-advertise_json_detail;
                    }
                }                  //detail
                leaf community_no-export_exact-match {
                    type enumeration {
                        enum community_no-export_exact-match;
                    }
                }                  //community_no-export_exact-match
                leaf community_no-export_exact-match_wide {
                    type enumeration {
                        enum community_no-export_exact-match_wide;
                    }
                }                  //wide
                leaf community_no-export_json {
                    type enumeration {
                        enum community_no-export_json;
                    }
                }                  //community_no-export_json
                leaf community_no-export_json_detail {
                    type enumeration {
                        enum community_no-export_json_detail;
                    }
                }                  //detail
                leaf community_graceful-shutdown_exact-match {
                    type enumeration {
                        enum community_graceful-shutdown_exact-match;
                    }
                }                  //community_graceful-shutdown_exact-match
                leaf community_graceful-shutdown_exact-match_wide {
                    type enumeration {
                        enum community_graceful-shutdown_exact-match_wide;
                    }
                }                  //wide
                leaf community_graceful-shutdown_json {
                    type enumeration {
                        enum community_graceful-shutdown_json;
                    }
                }                  //community_graceful-shutdown_json
                leaf community_graceful-shutdown_json_detail {
                    type enumeration {
                        enum community_graceful-shutdown_json_detail;
                    }
                }                  //detail
                leaf community_no-peer_exact-match {
                    type enumeration {
                        enum community_no-peer_exact-match;
                    }
                }                  //community_no-peer_exact-match
                leaf community_no-peer_exact-match_wide {
                    type enumeration {
                        enum community_no-peer_exact-match_wide;
                    }
                }                  //wide
                leaf community_no-peer_json {
                    type enumeration {
                        enum community_no-peer_json;
                    }
                }                  //community_no-peer_json
                leaf community_no-peer_json_detail {
                    type enumeration {
                        enum community_no-peer_json_detail;
                    }
                }                  //detail
                leaf community_blackhole_exact-match {
                    type enumeration {
                        enum community_blackhole_exact-match;
                    }
                }                  //community_blackhole_exact-match
                leaf community_blackhole_exact-match_wide {
                    type enumeration {
                        enum community_blackhole_exact-match_wide;
                    }
                }                  //wide
                leaf community_blackhole_json {
                    type enumeration {
                        enum community_blackhole_json;
                    }
                }                  //community_blackhole_json
                leaf community_blackhole_json_detail {
                    type enumeration {
                        enum community_blackhole_json_detail;
                    }
                }                  //detail
                leaf community_llgr-stale_exact-match {
                    type enumeration {
                        enum community_llgr-stale_exact-match;
                    }
                }                  //community_llgr-stale_exact-match
                leaf community_llgr-stale_exact-match_wide {
                    type enumeration {
                        enum community_llgr-stale_exact-match_wide;
                    }
                }                  //wide
                leaf community_llgr-stale_json {
                    type enumeration {
                        enum community_llgr-stale_json;
                    }
                }                  //community_llgr-stale_json
                leaf community_llgr-stale_json_detail {
                    type enumeration {
                        enum community_llgr-stale_json_detail;
                    }
                }                  //detail
                leaf community_no-llgr_exact-match {
                    type enumeration {
                        enum community_no-llgr_exact-match;
                    }
                }                  //community_no-llgr_exact-match
                leaf community_no-llgr_exact-match_wide {
                    type enumeration {
                        enum community_no-llgr_exact-match_wide;
                    }
                }                  //wide
                leaf community_no-llgr_json {
                    type enumeration {
                        enum community_no-llgr_json;
                    }
                }                  //community_no-llgr_json
                leaf community_no-llgr_json_detail {
                    type enumeration {
                        enum community_no-llgr_json_detail;
                    }
                }                  //detail
                leaf community_accept-own_exact-match {
                    type enumeration {
                        enum community_accept-own_exact-match;
                    }
                }                  //community_accept-own_exact-match
                leaf community_accept-own_exact-match_wide {
                    type enumeration {
                        enum community_accept-own_exact-match_wide;
                    }
                }                  //wide
                leaf community_accept-own_json {
                    type enumeration {
                        enum community_accept-own_json;
                    }
                }                  //community_accept-own_json
                leaf community_accept-own_json_detail {
                    type enumeration {
                        enum community_accept-own_json_detail;
                    }
                }                  //detail
                leaf community_accept-own-nexthop_exact-match {
                    type enumeration {
                        enum community_accept-own-nexthop_exact-match;
                    }
                }                  //community_accept-own-nexthop_exact-match
                leaf community_accept-own-nexthop_exact-match_wide {
                    type enumeration {
                        enum community_accept-own-nexthop_exact-match_wide;
                    }
                }                  //wide
                leaf community_accept-own-nexthop_json {
                    type enumeration {
                        enum community_accept-own-nexthop_json;
                    }
                }                  //community_accept-own-nexthop_json
                leaf community_accept-own-nexthop_json_detail {
                    type enumeration {
                        enum community_accept-own-nexthop_json_detail;
                    }
                }                  //detail
                leaf community_route-filter-v6_exact-match {
                    type enumeration {
                        enum community_route-filter-v6_exact-match;
                    }
                }                  //community_route-filter-v6_exact-match
                leaf community_route-filter-v6_exact-match_wide {
                    type enumeration {
                        enum community_route-filter-v6_exact-match_wide;
                    }
                }                  //wide
                leaf community_route-filter-v6_json {
                    type enumeration {
                        enum community_route-filter-v6_json;
                    }
                }                  //community_route-filter-v6_json
                leaf community_route-filter-v6_json_detail {
                    type enumeration {
                        enum community_route-filter-v6_json_detail;
                    }
                }                  //detail
                leaf community_route-filter-v4_exact-match {
                    type enumeration {
                        enum community_route-filter-v4_exact-match;
                    }
                }                  //community_route-filter-v4_exact-match
                leaf community_route-filter-v4_exact-match_wide {
                    type enumeration {
                        enum community_route-filter-v4_exact-match_wide;
                    }
                }                  //wide
                leaf community_route-filter-v4_json {
                    type enumeration {
                        enum community_route-filter-v4_json;
                    }
                }                  //community_route-filter-v4_json
                leaf community_route-filter-v4_json_detail {
                    type enumeration {
                        enum community_route-filter-v4_json_detail;
                    }
                }                  //detail
                leaf community_route-filter-translated-v6_exact-match {
                    type enumeration {
                        enum community_route-filter-translated-v6_exact-match;
                    }
                }                  //community_route-filter-translated-v6_exact-match
                leaf community_route-filter-translated-v6_exact-match_wide {
                    type enumeration {
                        enum community_route-filter-translated-v6_exact-match_wide;
                    }
                }                  //wide
                leaf community_route-filter-translated-v6_json {
                    type enumeration {
                        enum community_route-filter-translated-v6_json;
                    }
                }                  //community_route-filter-translated-v6_json
                leaf community_route-filter-translated-v6_json_detail {
                    type enumeration {
                        enum community_route-filter-translated-v6_json_detail;
                    }
                }                  //detail
                leaf community_route-filter-translated-v4_exact-match {
                    type enumeration {
                        enum community_route-filter-translated-v4_exact-match;
                    }
                }                  //community_route-filter-translated-v4_exact-match
                leaf community_route-filter-translated-v4_exact-match_wide {
                    type enumeration {
                        enum community_route-filter-translated-v4_exact-match_wide;
                    }
                }                  //wide
                leaf community_route-filter-translated-v4_json {
                    type enumeration {
                        enum community_route-filter-translated-v4_json;
                    }
                }                  //community_route-filter-translated-v4_json
                leaf community_route-filter-translated-v4_json_detail {
                    type enumeration {
                        enum community_route-filter-translated-v4_json_detail;
                    }
                }                  //detail
                leaf community_exact-match_json {
                    type enumeration {
                        enum community_exact-match_json;
                    }
                }                  //community_exact-match_json
                leaf community_exact-match_json_detail {
                    type enumeration {
                        enum community_exact-match_json_detail;
                    }
                }                  //detail
                leaf summary_established_terse {
                    type enumeration {
                        enum summary_established_terse;
                    }
                }                  //summary_established_terse
                leaf summary_established_terse_json {
                    type enumeration {
                        enum summary_established_terse_json;
                    }
                }                  //json
                leaf summary_established_wide {
                    type enumeration {
                        enum summary_established_wide;
                    }
                }                  //summary_established_wide
                leaf summary_established_wide_json {
                    type enumeration {
                        enum summary_established_wide_json;
                    }
                }                  //json
                leaf summary_failed_terse {
                    type enumeration {
                        enum summary_failed_terse;
                    }
                }                  //summary_failed_terse
                leaf summary_failed_terse_json {
                    type enumeration {
                        enum summary_failed_terse_json;
                    }
                }                  //json
                leaf summary_failed_wide {
                    type enumeration {
                        enum summary_failed_wide;
                    }
                }                  //summary_failed_wide
                leaf summary_failed_wide_json {
                    type enumeration {
                        enum summary_failed_wide_json;
                    }
                }                  //json
                leaf summary_terse_wide {
                    type enumeration {
                        enum summary_terse_wide;
                    }
                }                  //summary_terse_wide
                leaf summary_terse_wide_json {
                    type enumeration {
                        enum summary_terse_wide_json;
                    }
                }                  //json
                leaf all_community_local-AS_exact-match {
                    type enumeration {
                        enum all_community_local-AS_exact-match;
                    }
                }                  //all_community_local-AS_exact-match
                leaf all_community_local-AS_exact-match_wide {
                    type enumeration {
                        enum all_community_local-AS_exact-match_wide;
                    }
                }                  //wide
                leaf all_community_local-AS_json {
                    type enumeration {
                        enum all_community_local-AS_json;
                    }
                }                  //all_community_local-AS_json
                leaf all_community_local-AS_json_detail {
                    type enumeration {
                        enum all_community_local-AS_json_detail;
                    }
                }                  //detail
                leaf all_community_no-advertise_exact-match {
                    type enumeration {
                        enum all_community_no-advertise_exact-match;
                    }
                }                  //all_community_no-advertise_exact-match
                leaf all_community_no-advertise_exact-match_wide {
                    type enumeration {
                        enum all_community_no-advertise_exact-match_wide;
                    }
                }                  //wide
                leaf all_community_no-advertise_json {
                    type enumeration {
                        enum all_community_no-advertise_json;
                    }
                }                  //all_community_no-advertise_json
                leaf all_community_no-advertise_json_detail {
                    type enumeration {
                        enum all_community_no-advertise_json_detail;
                    }
                }                  //detail
                leaf all_community_no-export_exact-match {
                    type enumeration {
                        enum all_community_no-export_exact-match;
                    }
                }                  //all_community_no-export_exact-match
                leaf all_community_no-export_exact-match_wide {
                    type enumeration {
                        enum all_community_no-export_exact-match_wide;
                    }
                }                  //wide
                leaf all_community_no-export_json {
                    type enumeration {
                        enum all_community_no-export_json;
                    }
                }                  //all_community_no-export_json
                leaf all_community_no-export_json_detail {
                    type enumeration {
                        enum all_community_no-export_json_detail;
                    }
                }                  //detail
                leaf all_community_graceful-shutdown_exact-match {
                    type enumeration {
                        enum all_community_graceful-shutdown_exact-match;
                    }
                }                  //all_community_graceful-shutdown_exact-match
                leaf all_community_graceful-shutdown_exact-match_wide {
                    type enumeration {
                        enum all_community_graceful-shutdown_exact-match_wide;
                    }
                }                  //wide
                leaf all_community_graceful-shutdown_json {
                    type enumeration {
                        enum all_community_graceful-shutdown_json;
                    }
                }                  //all_community_graceful-shutdown_json
                leaf all_community_graceful-shutdown_json_detail {
                    type enumeration {
                        enum all_community_graceful-shutdown_json_detail;
                    }
                }                  //detail
                leaf all_community_no-peer_exact-match {
                    type enumeration {
                        enum all_community_no-peer_exact-match;
                    }
                }                  //all_community_no-peer_exact-match
                leaf all_community_no-peer_exact-match_wide {
                    type enumeration {
                        enum all_community_no-peer_exact-match_wide;
                    }
                }                  //wide
                leaf all_community_no-peer_json {
                    type enumeration {
                        enum all_community_no-peer_json;
                    }
                }                  //all_community_no-peer_json
                leaf all_community_no-peer_json_detail {
                    type enumeration {
                        enum all_community_no-peer_json_detail;
                    }
                }                  //detail
                leaf all_community_blackhole_exact-match {
                    type enumeration {
                        enum all_community_blackhole_exact-match;
                    }
                }                  //all_community_blackhole_exact-match
                leaf all_community_blackhole_exact-match_wide {
                    type enumeration {
                        enum all_community_blackhole_exact-match_wide;
                    }
                }                  //wide
                leaf all_community_blackhole_json {
                    type enumeration {
                        enum all_community_blackhole_json;
                    }
                }                  //all_community_blackhole_json
                leaf all_community_blackhole_json_detail {
                    type enumeration {
                        enum all_community_blackhole_json_detail;
                    }
                }                  //detail
                leaf all_community_llgr-stale_exact-match {
                    type enumeration {
                        enum all_community_llgr-stale_exact-match;
                    }
                }                  //all_community_llgr-stale_exact-match
                leaf all_community_llgr-stale_exact-match_wide {
                    type enumeration {
                        enum all_community_llgr-stale_exact-match_wide;
                    }
                }                  //wide
                leaf all_community_llgr-stale_json {
                    type enumeration {
                        enum all_community_llgr-stale_json;
                    }
                }                  //all_community_llgr-stale_json
                leaf all_community_llgr-stale_json_detail {
                    type enumeration {
                        enum all_community_llgr-stale_json_detail;
                    }
                }                  //detail
                leaf all_community_no-llgr_exact-match {
                    type enumeration {
                        enum all_community_no-llgr_exact-match;
                    }
                }                  //all_community_no-llgr_exact-match
                leaf all_community_no-llgr_exact-match_wide {
                    type enumeration {
                        enum all_community_no-llgr_exact-match_wide;
                    }
                }                  //wide
                leaf all_community_no-llgr_json {
                    type enumeration {
                        enum all_community_no-llgr_json;
                    }
                }                  //all_community_no-llgr_json
                leaf all_community_no-llgr_json_detail {
                    type enumeration {
                        enum all_community_no-llgr_json_detail;
                    }
                }                  //detail
                leaf all_community_accept-own_exact-match {
                    type enumeration {
                        enum all_community_accept-own_exact-match;
                    }
                }                  //all_community_accept-own_exact-match
                leaf all_community_accept-own_exact-match_wide {
                    type enumeration {
                        enum all_community_accept-own_exact-match_wide;
                    }
                }                  //wide
                leaf all_community_accept-own_json {
                    type enumeration {
                        enum all_community_accept-own_json;
                    }
                }                  //all_community_accept-own_json
                leaf all_community_accept-own_json_detail {
                    type enumeration {
                        enum all_community_accept-own_json_detail;
                    }
                }                  //detail
                leaf all_community_accept-own-nexthop_exact-match {
                    type enumeration {
                        enum all_community_accept-own-nexthop_exact-match;
                    }
                }                  //all_community_accept-own-nexthop_exact-match
                leaf all_community_accept-own-nexthop_exact-match_wide {
                    type enumeration {
                        enum all_community_accept-own-nexthop_exact-match_wide;
                    }
                }                  //wide
                leaf all_community_accept-own-nexthop_json {
                    type enumeration {
                        enum all_community_accept-own-nexthop_json;
                    }
                }                  //all_community_accept-own-nexthop_json
                leaf all_community_accept-own-nexthop_json_detail {
                    type enumeration {
                        enum all_community_accept-own-nexthop_json_detail;
                    }
                }                  //detail
                leaf all_community_route-filter-v6_exact-match {
                    type enumeration {
                        enum all_community_route-filter-v6_exact-match;
                    }
                }                  //all_community_route-filter-v6_exact-match
                leaf all_community_route-filter-v6_exact-match_wide {
                    type enumeration {
                        enum all_community_route-filter-v6_exact-match_wide;
                    }
                }                  //wide
                leaf all_community_route-filter-v6_json {
                    type enumeration {
                        enum all_community_route-filter-v6_json;
                    }
                }                  //all_community_route-filter-v6_json
                leaf all_community_route-filter-v6_json_detail {
                    type enumeration {
                        enum all_community_route-filter-v6_json_detail;
                    }
                }                  //detail
                leaf all_community_route-filter-v4_exact-match {
                    type enumeration {
                        enum all_community_route-filter-v4_exact-match;
                    }
                }                  //all_community_route-filter-v4_exact-match
                leaf all_community_route-filter-v4_exact-match_wide {
                    type enumeration {
                        enum all_community_route-filter-v4_exact-match_wide;
                    }
                }                  //wide
                leaf all_community_route-filter-v4_json {
                    type enumeration {
                        enum all_community_route-filter-v4_json;
                    }
                }                  //all_community_route-filter-v4_json
                leaf all_community_route-filter-v4_json_detail {
                    type enumeration {
                        enum all_community_route-filter-v4_json_detail;
                    }
                }                  //detail
                leaf all_community_route-filter-translated-v6_exact-match {
                    type enumeration {
                        enum all_community_route-filter-translated-v6_exact-match;
                    }
                }                  //all_community_route-filter-translated-v6_exact-match
                leaf all_community_route-filter-translated-v6_exact-match_wide {
                    type enumeration {
                        enum all_community_route-filter-translated-v6_exact-match_wide;
                    }
                }                  //wide
                leaf all_community_route-filter-translated-v6_json {
                    type enumeration {
                        enum all_community_route-filter-translated-v6_json;
                    }
                }                  //all_community_route-filter-translated-v6_json
                leaf all_community_route-filter-translated-v6_json_detail {
                    type enumeration {
                        enum all_community_route-filter-translated-v6_json_detail;
                    }
                }                  //detail
                leaf all_community_route-filter-translated-v4_exact-match {
                    type enumeration {
                        enum all_community_route-filter-translated-v4_exact-match;
                    }
                }                  //all_community_route-filter-translated-v4_exact-match
                leaf all_community_route-filter-translated-v4_exact-match_wide {
                    type enumeration {
                        enum all_community_route-filter-translated-v4_exact-match_wide;
                    }
                }                  //wide
                leaf all_community_route-filter-translated-v4_json {
                    type enumeration {
                        enum all_community_route-filter-translated-v4_json;
                    }
                }                  //all_community_route-filter-translated-v4_json
                leaf all_community_route-filter-translated-v4_json_detail {
                    type enumeration {
                        enum all_community_route-filter-translated-v4_json_detail;
                    }
                }                  //detail
                leaf all_community_exact-match_json {
                    type enumeration {
                        enum all_community_exact-match_json;
                    }
                }                  //all_community_exact-match_json
                leaf all_community_exact-match_json_detail {
                    type enumeration {
                        enum all_community_exact-match_json_detail;
                    }
                }                  //detail
                leaf all_summary_established_terse {
                    type enumeration {
                        enum all_summary_established_terse;
                    }
                }                  //all_summary_established_terse
                leaf all_summary_established_terse_json {
                    type enumeration {
                        enum all_summary_established_terse_json;
                    }
                }                  //json
                leaf all_summary_established_wide {
                    type enumeration {
                        enum all_summary_established_wide;
                    }
                }                  //all_summary_established_wide
                leaf all_summary_established_wide_json {
                    type enumeration {
                        enum all_summary_established_wide_json;
                    }
                }                  //json
                leaf all_summary_failed_terse {
                    type enumeration {
                        enum all_summary_failed_terse;
                    }
                }                  //all_summary_failed_terse
                leaf all_summary_failed_terse_json {
                    type enumeration {
                        enum all_summary_failed_terse_json;
                    }
                }                  //json
                leaf all_summary_failed_wide {
                    type enumeration {
                        enum all_summary_failed_wide;
                    }
                }                  //all_summary_failed_wide
                leaf all_summary_failed_wide_json {
                    type enumeration {
                        enum all_summary_failed_wide_json;
                    }
                }                  //json
                leaf all_summary_terse_wide {
                    type enumeration {
                        enum all_summary_terse_wide;
                    }
                }                  //all_summary_terse_wide
                leaf all_summary_terse_wide_json {
                    type enumeration {
                        enum all_summary_terse_wide_json;
                    }
                }                  //json
                leaf community_local-AS_exact-match_json {
                    type enumeration {
                        enum community_local-AS_exact-match_json;
                    }
                }                  //community_local-AS_exact-match_json
                leaf community_local-AS_exact-match_json_detail {
                    type enumeration {
                        enum community_local-AS_exact-match_json_detail;
                    }
                }                  //detail
                leaf community_no-advertise_exact-match_json {
                    type enumeration {
                        enum community_no-advertise_exact-match_json;
                    }
                }                  //community_no-advertise_exact-match_json
                leaf community_no-advertise_exact-match_json_detail {
                    type enumeration {
                        enum community_no-advertise_exact-match_json_detail;
                    }
                }                  //detail
                leaf community_no-export_exact-match_json {
                    type enumeration {
                        enum community_no-export_exact-match_json;
                    }
                }                  //community_no-export_exact-match_json
                leaf community_no-export_exact-match_json_detail {
                    type enumeration {
                        enum community_no-export_exact-match_json_detail;
                    }
                }                  //detail
                leaf community_graceful-shutdown_exact-match_json {
                    type enumeration {
                        enum community_graceful-shutdown_exact-match_json;
                    }
                }                  //community_graceful-shutdown_exact-match_json
                leaf community_graceful-shutdown_exact-match_json_detail {
                    type enumeration {
                        enum community_graceful-shutdown_exact-match_json_detail;
                    }
                }                  //detail
                leaf community_no-peer_exact-match_json {
                    type enumeration {
                        enum community_no-peer_exact-match_json;
                    }
                }                  //community_no-peer_exact-match_json
                leaf community_no-peer_exact-match_json_detail {
                    type enumeration {
                        enum community_no-peer_exact-match_json_detail;
                    }
                }                  //detail
                leaf community_blackhole_exact-match_json {
                    type enumeration {
                        enum community_blackhole_exact-match_json;
                    }
                }                  //community_blackhole_exact-match_json
                leaf community_blackhole_exact-match_json_detail {
                    type enumeration {
                        enum community_blackhole_exact-match_json_detail;
                    }
                }                  //detail
                leaf community_llgr-stale_exact-match_json {
                    type enumeration {
                        enum community_llgr-stale_exact-match_json;
                    }
                }                  //community_llgr-stale_exact-match_json
                leaf community_llgr-stale_exact-match_json_detail {
                    type enumeration {
                        enum community_llgr-stale_exact-match_json_detail;
                    }
                }                  //detail
                leaf community_no-llgr_exact-match_json {
                    type enumeration {
                        enum community_no-llgr_exact-match_json;
                    }
                }                  //community_no-llgr_exact-match_json
                leaf community_no-llgr_exact-match_json_detail {
                    type enumeration {
                        enum community_no-llgr_exact-match_json_detail;
                    }
                }                  //detail
                leaf community_accept-own_exact-match_json {
                    type enumeration {
                        enum community_accept-own_exact-match_json;
                    }
                }                  //community_accept-own_exact-match_json
                leaf community_accept-own_exact-match_json_detail {
                    type enumeration {
                        enum community_accept-own_exact-match_json_detail;
                    }
                }                  //detail
                leaf community_accept-own-nexthop_exact-match_json {
                    type enumeration {
                        enum community_accept-own-nexthop_exact-match_json;
                    }
                }                  //community_accept-own-nexthop_exact-match_json
                leaf community_accept-own-nexthop_exact-match_json_detail {
                    type enumeration {
                        enum community_accept-own-nexthop_exact-match_json_detail;
                    }
                }                  //detail
                leaf community_route-filter-v6_exact-match_json {
                    type enumeration {
                        enum community_route-filter-v6_exact-match_json;
                    }
                }                  //community_route-filter-v6_exact-match_json
                leaf community_route-filter-v6_exact-match_json_detail {
                    type enumeration {
                        enum community_route-filter-v6_exact-match_json_detail;
                    }
                }                  //detail
                leaf community_route-filter-v4_exact-match_json {
                    type enumeration {
                        enum community_route-filter-v4_exact-match_json;
                    }
                }                  //community_route-filter-v4_exact-match_json
                leaf community_route-filter-v4_exact-match_json_detail {
                    type enumeration {
                        enum community_route-filter-v4_exact-match_json_detail;
                    }
                }                  //detail
                leaf community_route-filter-translated-v6_exact-match_json {
                    type enumeration {
                        enum community_route-filter-translated-v6_exact-match_json;
                    }
                }                  //community_route-filter-translated-v6_exact-match_json
                leaf community_route-filter-translated-v6_exact-match_json_detail {
                    type enumeration {
                        enum community_route-filter-translated-v6_exact-match_json_detail;
                    }
                }                  //detail
                leaf community_route-filter-translated-v4_exact-match_json {
                    type enumeration {
                        enum community_route-filter-translated-v4_exact-match_json;
                    }
                }                  //community_route-filter-translated-v4_exact-match_json
                leaf community_route-filter-translated-v4_exact-match_json_detail {
                    type enumeration {
                        enum community_route-filter-translated-v4_exact-match_json_detail;
                    }
                }                  //detail
                leaf summary_established_terse_wide {
                    type enumeration {
                        enum summary_established_terse_wide;
                    }
                }                  //summary_established_terse_wide
                leaf summary_established_terse_wide_json {
                    type enumeration {
                        enum summary_established_terse_wide_json;
                    }
                }                  //json
                leaf summary_failed_terse_wide {
                    type enumeration {
                        enum summary_failed_terse_wide;
                    }
                }                  //summary_failed_terse_wide
                leaf summary_failed_terse_wide_json {
                    type enumeration {
                        enum summary_failed_terse_wide_json;
                    }
                }                  //json
                leaf all_community_local-AS_exact-match_json {
                    type enumeration {
                        enum all_community_local-AS_exact-match_json;
                    }
                }                  //all_community_local-AS_exact-match_json
                leaf all_community_local-AS_exact-match_json_detail {
                    type enumeration {
                        enum all_community_local-AS_exact-match_json_detail;
                    }
                }                  //detail
                leaf all_community_no-advertise_exact-match_json {
                    type enumeration {
                        enum all_community_no-advertise_exact-match_json;
                    }
                }                  //all_community_no-advertise_exact-match_json
                leaf all_community_no-advertise_exact-match_json_detail {
                    type enumeration {
                        enum all_community_no-advertise_exact-match_json_detail;
                    }
                }                  //detail
                leaf all_community_no-export_exact-match_json {
                    type enumeration {
                        enum all_community_no-export_exact-match_json;
                    }
                }                  //all_community_no-export_exact-match_json
                leaf all_community_no-export_exact-match_json_detail {
                    type enumeration {
                        enum all_community_no-export_exact-match_json_detail;
                    }
                }                  //detail
                leaf all_community_graceful-shutdown_exact-match_json {
                    type enumeration {
                        enum all_community_graceful-shutdown_exact-match_json;
                    }
                }                  //all_community_graceful-shutdown_exact-match_json
                leaf all_community_graceful-shutdown_exact-match_json_detail {
                    type enumeration {
                        enum all_community_graceful-shutdown_exact-match_json_detail;
                    }
                }                  //detail
                leaf all_community_no-peer_exact-match_json {
                    type enumeration {
                        enum all_community_no-peer_exact-match_json;
                    }
                }                  //all_community_no-peer_exact-match_json
                leaf all_community_no-peer_exact-match_json_detail {
                    type enumeration {
                        enum all_community_no-peer_exact-match_json_detail;
                    }
                }                  //detail
                leaf all_community_blackhole_exact-match_json {
                    type enumeration {
                        enum all_community_blackhole_exact-match_json;
                    }
                }                  //all_community_blackhole_exact-match_json
                leaf all_community_blackhole_exact-match_json_detail {
                    type enumeration {
                        enum all_community_blackhole_exact-match_json_detail;
                    }
                }                  //detail
                leaf all_community_llgr-stale_exact-match_json {
                    type enumeration {
                        enum all_community_llgr-stale_exact-match_json;
                    }
                }                  //all_community_llgr-stale_exact-match_json
                leaf all_community_llgr-stale_exact-match_json_detail {
                    type enumeration {
                        enum all_community_llgr-stale_exact-match_json_detail;
                    }
                }                  //detail
                leaf all_community_no-llgr_exact-match_json {
                    type enumeration {
                        enum all_community_no-llgr_exact-match_json;
                    }
                }                  //all_community_no-llgr_exact-match_json
                leaf all_community_no-llgr_exact-match_json_detail {
                    type enumeration {
                        enum all_community_no-llgr_exact-match_json_detail;
                    }
                }                  //detail
                leaf all_community_accept-own_exact-match_json {
                    type enumeration {
                        enum all_community_accept-own_exact-match_json;
                    }
                }                  //all_community_accept-own_exact-match_json
                leaf all_community_accept-own_exact-match_json_detail {
                    type enumeration {
                        enum all_community_accept-own_exact-match_json_detail;
                    }
                }                  //detail
                leaf all_community_accept-own-nexthop_exact-match_json {
                    type enumeration {
                        enum all_community_accept-own-nexthop_exact-match_json;
                    }
                }                  //all_community_accept-own-nexthop_exact-match_json
                leaf all_community_accept-own-nexthop_exact-match_json_detail {
                    type enumeration {
                        enum all_community_accept-own-nexthop_exact-match_json_detail;
                    }
                }                  //detail
                leaf all_community_route-filter-v6_exact-match_json {
                    type enumeration {
                        enum all_community_route-filter-v6_exact-match_json;
                    }
                }                  //all_community_route-filter-v6_exact-match_json
                leaf all_community_route-filter-v6_exact-match_json_detail {
                    type enumeration {
                        enum all_community_route-filter-v6_exact-match_json_detail;
                    }
                }                  //detail
                leaf all_community_route-filter-v4_exact-match_json {
                    type enumeration {
                        enum all_community_route-filter-v4_exact-match_json;
                    }
                }                  //all_community_route-filter-v4_exact-match_json
                leaf all_community_route-filter-v4_exact-match_json_detail {
                    type enumeration {
                        enum all_community_route-filter-v4_exact-match_json_detail;
                    }
                }                  //detail
                leaf all_community_route-filter-translated-v6_exact-match_json {
                    type enumeration {
                        enum all_community_route-filter-translated-v6_exact-match_json;
                    }
                }                  //all_community_route-filter-translated-v6_exact-match_json
                leaf all_community_route-filter-translated-v6_exact-match_json_detail {
                    type enumeration {
                        enum all_community_route-filter-translated-v6_exact-match_json_detail;
                    }
                }                  //detail
                leaf all_community_route-filter-translated-v4_exact-match_json {
                    type enumeration {
                        enum all_community_route-filter-translated-v4_exact-match_json;
                    }
                }                  //all_community_route-filter-translated-v4_exact-match_json
                leaf all_community_route-filter-translated-v4_exact-match_json_detail {
                    type enumeration {
                        enum all_community_route-filter-translated-v4_exact-match_json_detail;
                    }
                }                  //detail
                leaf all_summary_established_terse_wide {
                    type enumeration {
                        enum all_summary_established_terse_wide;
                    }
                }                  //all_summary_established_terse_wide
                leaf all_summary_established_terse_wide_json {
                    type enumeration {
                        enum all_summary_established_terse_wide_json;
                    }
                }                  //json
                leaf all_summary_failed_terse_wide {
                    type enumeration {
                        enum all_summary_failed_terse_wide;
                    }
                }                  //all_summary_failed_terse_wide
                leaf all_summary_failed_terse_wide_json {
                    type enumeration {
                        enum all_summary_failed_terse_wide_json;
                    }
                }                  //json
                leaf neighbors_graceful-restart {
                    type enumeration {
                        enum neighbors_graceful-restart;
                    }
                }                  //neighbors_graceful-restart
                leaf neighbors_graceful-restart_json {
                    type enumeration {
                        enum neighbors_graceful-restart_json;
                    }
                }                  //json
                leaf unicast_all {
                    type enumeration {
                        enum unicast_all;
                    }
                }                  //unicast_all
                leaf unicast_all_community-list {
                    type enumeration {
                        enum unicast_all_community-list;
                    }
                }                  //community-list
                leaf unicast_all_filter-list {
                    type enumeration {
                        enum unicast_all_filter-list;
                    }
                }                  //filter-list
                leaf unicast_all_prefix-list {
                    type enumeration {
                        enum unicast_all_prefix-list;
                    }
                }                  //prefix-list
                leaf unicast_all_access-list {
                    type enumeration {
                        enum unicast_all_access-list;
                    }
                }                  //access-list
                leaf unicast_all_route-map {
                    type enumeration {
                        enum unicast_all_route-map;
                    }
                }                  //route-map
                leaf unicast_all_rpki {
                    type enumeration {
                        enum unicast_all_rpki;
                    }
                }                  //rpki
                leaf unicast_all_version {
                    type enumeration {
                        enum unicast_all_version;
                    }
                }                  //version
                leaf unicast_all_alias {
                    type enumeration {
                        enum unicast_all_alias;
                    }
                }                  //alias
                leaf unicast_all_wide {
                    type enumeration {
                        enum unicast_all_wide;
                    }
                }                  //wide
                leaf unicast_all_neighbors {
                    type enumeration {
                        enum unicast_all_neighbors;
                    }
                }                  //neighbors
                leaf unicast_cidr-only {
                    type enumeration {
                        enum unicast_cidr-only;
                    }
                }                  //unicast_cidr-only
                leaf unicast_cidr-only_wide {
                    type enumeration {
                        enum unicast_cidr-only_wide;
                    }
                }                  //wide
                leaf unicast_dampening {
                    type enumeration {
                        enum unicast_dampening;
                    }
                }                  //unicast_dampening
                leaf unicast_community {
                    type enumeration {
                        enum unicast_community;
                    }
                }                  //unicast_community
                leaf unicast_community_wide {
                    type enumeration {
                        enum unicast_community_wide;
                    }
                }                  //wide
                leaf unicast_detail-routes {
                    type enumeration {
                        enum unicast_detail-routes;
                    }
                }                  //unicast_detail-routes
                leaf unicast_detail-routes_wide {
                    type enumeration {
                        enum unicast_detail-routes_wide;
                    }
                }                  //wide
                leaf unicast_json {
                    type enumeration {
                        enum unicast_json;
                    }
                }                  //unicast_json
                leaf unicast_json_detail {
                    type enumeration {
                        enum unicast_json_detail;
                    }
                }                  //detail
                leaf unicast_summary {
                    type enumeration {
                        enum unicast_summary;
                    }
                }                  //unicast_summary
                leaf unicast_summary_neighbor {
                    type enumeration {
                        enum unicast_summary_neighbor;
                    }
                }                  //neighbor
                leaf unicast_summary_remote-as {
                    type enumeration {
                        enum unicast_summary_remote-as;
                    }
                }                  //remote-as
                leaf unicast_summary_json {
                    type enumeration {
                        enum unicast_summary_json;
                    }
                }                  //json
                leaf unicast_large-community {
                    type enumeration {
                        enum unicast_large-community;
                    }
                }                  //unicast_large-community
                leaf unicast_large-community_json {
                    type enumeration {
                        enum unicast_large-community_json;
                    }
                }                  //json
                leaf unicast_statistics {
                    type enumeration {
                        enum unicast_statistics;
                    }
                }                  //unicast_statistics
                leaf unicast_statistics_json {
                    type enumeration {
                        enum unicast_statistics_json;
                    }
                }                  //json
                leaf unicast_update-groups {
                    type enumeration {
                        enum unicast_update-groups;
                    }
                }                  //unicast_update-groups
                leaf unicast_update-groups_json {
                    type enumeration {
                        enum unicast_update-groups_json;
                    }
                }                  //json
                leaf flowspec_all {
                    type enumeration {
                        enum flowspec_all;
                    }
                }                  //flowspec_all
                leaf flowspec_all_community-list {
                    type enumeration {
                        enum flowspec_all_community-list;
                    }
                }                  //community-list
                leaf flowspec_all_filter-list {
                    type enumeration {
                        enum flowspec_all_filter-list;
                    }
                }                  //filter-list
                leaf flowspec_all_prefix-list {
                    type enumeration {
                        enum flowspec_all_prefix-list;
                    }
                }                  //prefix-list
                leaf flowspec_all_access-list {
                    type enumeration {
                        enum flowspec_all_access-list;
                    }
                }                  //access-list
                leaf flowspec_all_route-map {
                    type enumeration {
                        enum flowspec_all_route-map;
                    }
                }                  //route-map
                leaf flowspec_all_rpki {
                    type enumeration {
                        enum flowspec_all_rpki;
                    }
                }                  //rpki
                leaf flowspec_all_version {
                    type enumeration {
                        enum flowspec_all_version;
                    }
                }                  //version
                leaf flowspec_all_alias {
                    type enumeration {
                        enum flowspec_all_alias;
                    }
                }                  //alias
                leaf flowspec_all_wide {
                    type enumeration {
                        enum flowspec_all_wide;
                    }
                }                  //wide
                leaf flowspec_all_neighbors {
                    type enumeration {
                        enum flowspec_all_neighbors;
                    }
                }                  //neighbors
                leaf flowspec_cidr-only {
                    type enumeration {
                        enum flowspec_cidr-only;
                    }
                }                  //flowspec_cidr-only
                leaf flowspec_cidr-only_wide {
                    type enumeration {
                        enum flowspec_cidr-only_wide;
                    }
                }                  //wide
                leaf flowspec_dampening {
                    type enumeration {
                        enum flowspec_dampening;
                    }
                }                  //flowspec_dampening
                leaf flowspec_community {
                    type enumeration {
                        enum flowspec_community;
                    }
                }                  //flowspec_community
                leaf flowspec_community_wide {
                    type enumeration {
                        enum flowspec_community_wide;
                    }
                }                  //wide
                leaf flowspec_detail-routes {
                    type enumeration {
                        enum flowspec_detail-routes;
                    }
                }                  //flowspec_detail-routes
                leaf flowspec_detail-routes_wide {
                    type enumeration {
                        enum flowspec_detail-routes_wide;
                    }
                }                  //wide
                leaf flowspec_json {
                    type enumeration {
                        enum flowspec_json;
                    }
                }                  //flowspec_json
                leaf flowspec_json_detail {
                    type enumeration {
                        enum flowspec_json_detail;
                    }
                }                  //detail
                leaf flowspec_summary {
                    type enumeration {
                        enum flowspec_summary;
                    }
                }                  //flowspec_summary
                leaf flowspec_summary_neighbor {
                    type enumeration {
                        enum flowspec_summary_neighbor;
                    }
                }                  //neighbor
                leaf flowspec_summary_remote-as {
                    type enumeration {
                        enum flowspec_summary_remote-as;
                    }
                }                  //remote-as
                leaf flowspec_summary_json {
                    type enumeration {
                        enum flowspec_summary_json;
                    }
                }                  //json
                leaf flowspec_large-community {
                    type enumeration {
                        enum flowspec_large-community;
                    }
                }                  //flowspec_large-community
                leaf flowspec_large-community_json {
                    type enumeration {
                        enum flowspec_large-community_json;
                    }
                }                  //json
                leaf flowspec_statistics {
                    type enumeration {
                        enum flowspec_statistics;
                    }
                }                  //flowspec_statistics
                leaf flowspec_statistics_json {
                    type enumeration {
                        enum flowspec_statistics_json;
                    }
                }                  //json
                leaf flowspec_update-groups {
                    type enumeration {
                        enum flowspec_update-groups;
                    }
                }                  //flowspec_update-groups
                leaf flowspec_update-groups_json {
                    type enumeration {
                        enum flowspec_update-groups_json;
                    }
                }                  //json
                leaf flowspec_detail {
                    type enumeration {
                        enum flowspec_detail;
                    }
                }                  //flowspec_detail
                leaf flowspec_detail_json {
                    type enumeration {
                        enum flowspec_detail_json;
                    }
                }                  //json
                leaf vpn_all {
                    type enumeration {
                        enum vpn_all;
                    }
                }                  //vpn_all
                leaf vpn_all_community-list {
                    type enumeration {
                        enum vpn_all_community-list;
                    }
                }                  //community-list
                leaf vpn_all_filter-list {
                    type enumeration {
                        enum vpn_all_filter-list;
                    }
                }                  //filter-list
                leaf vpn_all_prefix-list {
                    type enumeration {
                        enum vpn_all_prefix-list;
                    }
                }                  //prefix-list
                leaf vpn_all_access-list {
                    type enumeration {
                        enum vpn_all_access-list;
                    }
                }                  //access-list
                leaf vpn_all_route-map {
                    type enumeration {
                        enum vpn_all_route-map;
                    }
                }                  //route-map
                leaf vpn_all_rpki {
                    type enumeration {
                        enum vpn_all_rpki;
                    }
                }                  //rpki
                leaf vpn_all_version {
                    type enumeration {
                        enum vpn_all_version;
                    }
                }                  //version
                leaf vpn_all_alias {
                    type enumeration {
                        enum vpn_all_alias;
                    }
                }                  //alias
                leaf vpn_all_wide {
                    type enumeration {
                        enum vpn_all_wide;
                    }
                }                  //wide
                leaf vpn_all_neighbors {
                    type enumeration {
                        enum vpn_all_neighbors;
                    }
                }                  //neighbors
                leaf vpn_cidr-only {
                    type enumeration {
                        enum vpn_cidr-only;
                    }
                }                  //vpn_cidr-only
                leaf vpn_cidr-only_wide {
                    type enumeration {
                        enum vpn_cidr-only_wide;
                    }
                }                  //wide
                leaf vpn_dampening {
                    type enumeration {
                        enum vpn_dampening;
                    }
                }                  //vpn_dampening
                leaf vpn_community {
                    type enumeration {
                        enum vpn_community;
                    }
                }                  //vpn_community
                leaf vpn_community_wide {
                    type enumeration {
                        enum vpn_community_wide;
                    }
                }                  //wide
                leaf vpn_detail-routes {
                    type enumeration {
                        enum vpn_detail-routes;
                    }
                }                  //vpn_detail-routes
                leaf vpn_detail-routes_wide {
                    type enumeration {
                        enum vpn_detail-routes_wide;
                    }
                }                  //wide
                leaf vpn_json {
                    type enumeration {
                        enum vpn_json;
                    }
                }                  //vpn_json
                leaf vpn_json_detail {
                    type enumeration {
                        enum vpn_json_detail;
                    }
                }                  //detail
                leaf vpn_summary {
                    type enumeration {
                        enum vpn_summary;
                    }
                }                  //vpn_summary
                leaf vpn_summary_neighbor {
                    type enumeration {
                        enum vpn_summary_neighbor;
                    }
                }                  //neighbor
                leaf vpn_summary_remote-as {
                    type enumeration {
                        enum vpn_summary_remote-as;
                    }
                }                  //remote-as
                leaf vpn_summary_json {
                    type enumeration {
                        enum vpn_summary_json;
                    }
                }                  //json
                leaf vpn_large-community {
                    type enumeration {
                        enum vpn_large-community;
                    }
                }                  //vpn_large-community
                leaf vpn_large-community_json {
                    type enumeration {
                        enum vpn_large-community_json;
                    }
                }                  //json
                leaf vpn_statistics {
                    type enumeration {
                        enum vpn_statistics;
                    }
                }                  //vpn_statistics
                leaf vpn_statistics_json {
                    type enumeration {
                        enum vpn_statistics_json;
                    }
                }                  //json
                leaf vpn_update-groups {
                    type enumeration {
                        enum vpn_update-groups;
                    }
                }                  //vpn_update-groups
                leaf vpn_update-groups_json {
                    type enumeration {
                        enum vpn_update-groups_json;
                    }
                }                  //json
                leaf multicast_update-groups {
                    type enumeration {
                        enum multicast_update-groups;
                    }
                }                  //multicast_update-groups
                leaf SPECIFIC_SUBGROUP_TO_DISPLAY {
                    type string;
                }                  //SUBGROUP-ID
                leaf ROUTING_QUEUE {
                    type enumeration {
                        enum advertise-queue;
                        enum advertised-routes;
                        enum packet-queue;
                    }
                }                  //<advertise-queue|advertised-routes|packet-queue> ['Advertisement queue', 'Announced routes', 'Packet queue']
                leaf multicast_route-leak {
                    type enumeration {
                        enum multicast_route-leak;
                    }
                }                  //multicast_route-leak
                leaf multicast_route-leak_json {
                    type enumeration {
                        enum multicast_route-leak_json;
                    }
                }                  //json
                leaf unicast_all_cidr-only {
                    type enumeration {
                        enum unicast_all_cidr-only;
                    }
                }                  //unicast_all_cidr-only
                leaf unicast_all_cidr-only_wide {
                    type enumeration {
                        enum unicast_all_cidr-only_wide;
                    }
                }                  //wide
                leaf unicast_all_dampening {
                    type enumeration {
                        enum unicast_all_dampening;
                    }
                }                  //unicast_all_dampening
                leaf unicast_all_community {
                    type enumeration {
                        enum unicast_all_community;
                    }
                }                  //unicast_all_community
                leaf unicast_all_community_wide {
                    type enumeration {
                        enum unicast_all_community_wide;
                    }
                }                  //wide
                leaf unicast_all_detail-routes {
                    type enumeration {
                        enum unicast_all_detail-routes;
                    }
                }                  //unicast_all_detail-routes
                leaf unicast_all_detail-routes_wide {
                    type enumeration {
                        enum unicast_all_detail-routes_wide;
                    }
                }                  //wide
                leaf unicast_all_json {
                    type enumeration {
                        enum unicast_all_json;
                    }
                }                  //unicast_all_json
                leaf unicast_all_json_detail {
                    type enumeration {
                        enum unicast_all_json_detail;
                    }
                }                  //detail
                leaf unicast_all_summary {
                    type enumeration {
                        enum unicast_all_summary;
                    }
                }                  //unicast_all_summary
                leaf unicast_all_summary_neighbor {
                    type enumeration {
                        enum unicast_all_summary_neighbor;
                    }
                }                  //neighbor
                leaf unicast_all_summary_remote-as {
                    type enumeration {
                        enum unicast_all_summary_remote-as;
                    }
                }                  //remote-as
                leaf unicast_all_summary_json {
                    type enumeration {
                        enum unicast_all_summary_json;
                    }
                }                  //json
                leaf unicast_cidr-only_json {
                    type enumeration {
                        enum unicast_cidr-only_json;
                    }
                }                  //unicast_cidr-only_json
                leaf unicast_cidr-only_json_detail {
                    type enumeration {
                        enum unicast_cidr-only_json_detail;
                    }
                }                  //detail
                leaf unicast_dampening_parameters {
                    type enumeration {
                        enum unicast_dampening_parameters;
                    }
                }                  //unicast_dampening_parameters
                leaf unicast_dampening_parameters_json {
                    type enumeration {
                        enum unicast_dampening_parameters_json;
                    }
                }                  //json
                leaf unicast_community_local-AS {
                    type enumeration {
                        enum unicast_community_local-AS;
                    }
                }                  //unicast_community_local-AS
                leaf unicast_community_local-AS_wide {
                    type enumeration {
                        enum unicast_community_local-AS_wide;
                    }
                }                  //wide
                leaf unicast_community_no-advertise {
                    type enumeration {
                        enum unicast_community_no-advertise;
                    }
                }                  //unicast_community_no-advertise
                leaf unicast_community_no-advertise_wide {
                    type enumeration {
                        enum unicast_community_no-advertise_wide;
                    }
                }                  //wide
                leaf unicast_community_no-export {
                    type enumeration {
                        enum unicast_community_no-export;
                    }
                }                  //unicast_community_no-export
                leaf unicast_community_no-export_wide {
                    type enumeration {
                        enum unicast_community_no-export_wide;
                    }
                }                  //wide
                leaf unicast_community_graceful-shutdown {
                    type enumeration {
                        enum unicast_community_graceful-shutdown;
                    }
                }                  //unicast_community_graceful-shutdown
                leaf unicast_community_graceful-shutdown_wide {
                    type enumeration {
                        enum unicast_community_graceful-shutdown_wide;
                    }
                }                  //wide
                leaf unicast_community_no-peer {
                    type enumeration {
                        enum unicast_community_no-peer;
                    }
                }                  //unicast_community_no-peer
                leaf unicast_community_no-peer_wide {
                    type enumeration {
                        enum unicast_community_no-peer_wide;
                    }
                }                  //wide
                leaf unicast_community_blackhole {
                    type enumeration {
                        enum unicast_community_blackhole;
                    }
                }                  //unicast_community_blackhole
                leaf unicast_community_blackhole_wide {
                    type enumeration {
                        enum unicast_community_blackhole_wide;
                    }
                }                  //wide
                leaf unicast_community_llgr-stale {
                    type enumeration {
                        enum unicast_community_llgr-stale;
                    }
                }                  //unicast_community_llgr-stale
                leaf unicast_community_llgr-stale_wide {
                    type enumeration {
                        enum unicast_community_llgr-stale_wide;
                    }
                }                  //wide
                leaf unicast_community_no-llgr {
                    type enumeration {
                        enum unicast_community_no-llgr;
                    }
                }                  //unicast_community_no-llgr
                leaf unicast_community_no-llgr_wide {
                    type enumeration {
                        enum unicast_community_no-llgr_wide;
                    }
                }                  //wide
                leaf unicast_community_accept-own {
                    type enumeration {
                        enum unicast_community_accept-own;
                    }
                }                  //unicast_community_accept-own
                leaf unicast_community_accept-own_wide {
                    type enumeration {
                        enum unicast_community_accept-own_wide;
                    }
                }                  //wide
                leaf unicast_community_accept-own-nexthop {
                    type enumeration {
                        enum unicast_community_accept-own-nexthop;
                    }
                }                  //unicast_community_accept-own-nexthop
                leaf unicast_community_accept-own-nexthop_wide {
                    type enumeration {
                        enum unicast_community_accept-own-nexthop_wide;
                    }
                }                  //wide
                leaf unicast_community_route-filter-v6 {
                    type enumeration {
                        enum unicast_community_route-filter-v6;
                    }
                }                  //unicast_community_route-filter-v6
                leaf unicast_community_route-filter-v6_wide {
                    type enumeration {
                        enum unicast_community_route-filter-v6_wide;
                    }
                }                  //wide
                leaf unicast_community_route-filter-v4 {
                    type enumeration {
                        enum unicast_community_route-filter-v4;
                    }
                }                  //unicast_community_route-filter-v4
                leaf unicast_community_route-filter-v4_wide {
                    type enumeration {
                        enum unicast_community_route-filter-v4_wide;
                    }
                }                  //wide
                leaf unicast_community_route-filter-translated-v6 {
                    type enumeration {
                        enum unicast_community_route-filter-translated-v6;
                    }
                }                  //unicast_community_route-filter-translated-v6
                leaf unicast_community_route-filter-translated-v6_wide {
                    type enumeration {
                        enum unicast_community_route-filter-translated-v6_wide;
                    }
                }                  //wide
                leaf unicast_community_route-filter-translated-v4 {
                    type enumeration {
                        enum unicast_community_route-filter-translated-v4;
                    }
                }                  //unicast_community_route-filter-translated-v4
                leaf unicast_community_route-filter-translated-v4_wide {
                    type enumeration {
                        enum unicast_community_route-filter-translated-v4_wide;
                    }
                }                  //wide
                leaf unicast_community_exact-match {
                    type enumeration {
                        enum unicast_community_exact-match;
                    }
                }                  //unicast_community_exact-match
                leaf unicast_community_exact-match_wide {
                    type enumeration {
                        enum unicast_community_exact-match_wide;
                    }
                }                  //wide
                leaf unicast_community_json {
                    type enumeration {
                        enum unicast_community_json;
                    }
                }                  //unicast_community_json
                leaf unicast_community_json_detail {
                    type enumeration {
                        enum unicast_community_json_detail;
                    }
                }                  //detail
                leaf unicast_detail-routes_json {
                    type enumeration {
                        enum unicast_detail-routes_json;
                    }
                }                  //unicast_detail-routes_json
                leaf unicast_detail-routes_json_detail {
                    type enumeration {
                        enum unicast_detail-routes_json_detail;
                    }
                }                  //detail
                leaf unicast_summary_established {
                    type enumeration {
                        enum unicast_summary_established;
                    }
                }                  //unicast_summary_established
                leaf unicast_summary_established_neighbor {
                    type enumeration {
                        enum unicast_summary_established_neighbor;
                    }
                }                  //neighbor
                leaf unicast_summary_established_remote-as {
                    type enumeration {
                        enum unicast_summary_established_remote-as;
                    }
                }                  //remote-as
                leaf unicast_summary_established_json {
                    type enumeration {
                        enum unicast_summary_established_json;
                    }
                }                  //json
                leaf unicast_summary_failed {
                    type enumeration {
                        enum unicast_summary_failed;
                    }
                }                  //unicast_summary_failed
                leaf unicast_summary_failed_neighbor {
                    type enumeration {
                        enum unicast_summary_failed_neighbor;
                    }
                }                  //neighbor
                leaf unicast_summary_failed_remote-as {
                    type enumeration {
                        enum unicast_summary_failed_remote-as;
                    }
                }                  //remote-as
                leaf unicast_summary_failed_json {
                    type enumeration {
                        enum unicast_summary_failed_json;
                    }
                }                  //json
                leaf unicast_summary_terse {
                    type enumeration {
                        enum unicast_summary_terse;
                    }
                }                  //unicast_summary_terse
                leaf unicast_summary_terse_json {
                    type enumeration {
                        enum unicast_summary_terse_json;
                    }
                }                  //json
                leaf unicast_summary_wide {
                    type enumeration {
                        enum unicast_summary_wide;
                    }
                }                  //unicast_summary_wide
                leaf unicast_summary_wide_json {
                    type enumeration {
                        enum unicast_summary_wide_json;
                    }
                }                  //json
                leaf flowspec_all_cidr-only {
                    type enumeration {
                        enum flowspec_all_cidr-only;
                    }
                }                  //flowspec_all_cidr-only
                leaf flowspec_all_cidr-only_wide {
                    type enumeration {
                        enum flowspec_all_cidr-only_wide;
                    }
                }                  //wide
                leaf flowspec_all_dampening {
                    type enumeration {
                        enum flowspec_all_dampening;
                    }
                }                  //flowspec_all_dampening
                leaf flowspec_all_community {
                    type enumeration {
                        enum flowspec_all_community;
                    }
                }                  //flowspec_all_community
                leaf flowspec_all_community_wide {
                    type enumeration {
                        enum flowspec_all_community_wide;
                    }
                }                  //wide
                leaf flowspec_all_detail-routes {
                    type enumeration {
                        enum flowspec_all_detail-routes;
                    }
                }                  //flowspec_all_detail-routes
                leaf flowspec_all_detail-routes_wide {
                    type enumeration {
                        enum flowspec_all_detail-routes_wide;
                    }
                }                  //wide
                leaf flowspec_all_json {
                    type enumeration {
                        enum flowspec_all_json;
                    }
                }                  //flowspec_all_json
                leaf flowspec_all_json_detail {
                    type enumeration {
                        enum flowspec_all_json_detail;
                    }
                }                  //detail
                leaf flowspec_all_summary {
                    type enumeration {
                        enum flowspec_all_summary;
                    }
                }                  //flowspec_all_summary
                leaf flowspec_all_summary_neighbor {
                    type enumeration {
                        enum flowspec_all_summary_neighbor;
                    }
                }                  //neighbor
                leaf flowspec_all_summary_remote-as {
                    type enumeration {
                        enum flowspec_all_summary_remote-as;
                    }
                }                  //remote-as
                leaf flowspec_all_summary_json {
                    type enumeration {
                        enum flowspec_all_summary_json;
                    }
                }                  //json
                leaf flowspec_cidr-only_json {
                    type enumeration {
                        enum flowspec_cidr-only_json;
                    }
                }                  //flowspec_cidr-only_json
                leaf flowspec_cidr-only_json_detail {
                    type enumeration {
                        enum flowspec_cidr-only_json_detail;
                    }
                }                  //detail
                leaf flowspec_dampening_parameters {
                    type enumeration {
                        enum flowspec_dampening_parameters;
                    }
                }                  //flowspec_dampening_parameters
                leaf flowspec_dampening_parameters_json {
                    type enumeration {
                        enum flowspec_dampening_parameters_json;
                    }
                }                  //json
                leaf flowspec_community_local-AS {
                    type enumeration {
                        enum flowspec_community_local-AS;
                    }
                }                  //flowspec_community_local-AS
                leaf flowspec_community_local-AS_wide {
                    type enumeration {
                        enum flowspec_community_local-AS_wide;
                    }
                }                  //wide
                leaf flowspec_community_no-advertise {
                    type enumeration {
                        enum flowspec_community_no-advertise;
                    }
                }                  //flowspec_community_no-advertise
                leaf flowspec_community_no-advertise_wide {
                    type enumeration {
                        enum flowspec_community_no-advertise_wide;
                    }
                }                  //wide
                leaf flowspec_community_no-export {
                    type enumeration {
                        enum flowspec_community_no-export;
                    }
                }                  //flowspec_community_no-export
                leaf flowspec_community_no-export_wide {
                    type enumeration {
                        enum flowspec_community_no-export_wide;
                    }
                }                  //wide
                leaf flowspec_community_graceful-shutdown {
                    type enumeration {
                        enum flowspec_community_graceful-shutdown;
                    }
                }                  //flowspec_community_graceful-shutdown
                leaf flowspec_community_graceful-shutdown_wide {
                    type enumeration {
                        enum flowspec_community_graceful-shutdown_wide;
                    }
                }                  //wide
                leaf flowspec_community_no-peer {
                    type enumeration {
                        enum flowspec_community_no-peer;
                    }
                }                  //flowspec_community_no-peer
                leaf flowspec_community_no-peer_wide {
                    type enumeration {
                        enum flowspec_community_no-peer_wide;
                    }
                }                  //wide
                leaf flowspec_community_blackhole {
                    type enumeration {
                        enum flowspec_community_blackhole;
                    }
                }                  //flowspec_community_blackhole
                leaf flowspec_community_blackhole_wide {
                    type enumeration {
                        enum flowspec_community_blackhole_wide;
                    }
                }                  //wide
                leaf flowspec_community_llgr-stale {
                    type enumeration {
                        enum flowspec_community_llgr-stale;
                    }
                }                  //flowspec_community_llgr-stale
                leaf flowspec_community_llgr-stale_wide {
                    type enumeration {
                        enum flowspec_community_llgr-stale_wide;
                    }
                }                  //wide
                leaf flowspec_community_no-llgr {
                    type enumeration {
                        enum flowspec_community_no-llgr;
                    }
                }                  //flowspec_community_no-llgr
                leaf flowspec_community_no-llgr_wide {
                    type enumeration {
                        enum flowspec_community_no-llgr_wide;
                    }
                }                  //wide
                leaf flowspec_community_accept-own {
                    type enumeration {
                        enum flowspec_community_accept-own;
                    }
                }                  //flowspec_community_accept-own
                leaf flowspec_community_accept-own_wide {
                    type enumeration {
                        enum flowspec_community_accept-own_wide;
                    }
                }                  //wide
                leaf flowspec_community_accept-own-nexthop {
                    type enumeration {
                        enum flowspec_community_accept-own-nexthop;
                    }
                }                  //flowspec_community_accept-own-nexthop
                leaf flowspec_community_accept-own-nexthop_wide {
                    type enumeration {
                        enum flowspec_community_accept-own-nexthop_wide;
                    }
                }                  //wide
                leaf flowspec_community_route-filter-v6 {
                    type enumeration {
                        enum flowspec_community_route-filter-v6;
                    }
                }                  //flowspec_community_route-filter-v6
                leaf flowspec_community_route-filter-v6_wide {
                    type enumeration {
                        enum flowspec_community_route-filter-v6_wide;
                    }
                }                  //wide
                leaf flowspec_community_route-filter-v4 {
                    type enumeration {
                        enum flowspec_community_route-filter-v4;
                    }
                }                  //flowspec_community_route-filter-v4
                leaf flowspec_community_route-filter-v4_wide {
                    type enumeration {
                        enum flowspec_community_route-filter-v4_wide;
                    }
                }                  //wide
                leaf flowspec_community_route-filter-translated-v6 {
                    type enumeration {
                        enum flowspec_community_route-filter-translated-v6;
                    }
                }                  //flowspec_community_route-filter-translated-v6
                leaf flowspec_community_route-filter-translated-v6_wide {
                    type enumeration {
                        enum flowspec_community_route-filter-translated-v6_wide;
                    }
                }                  //wide
                leaf flowspec_community_route-filter-translated-v4 {
                    type enumeration {
                        enum flowspec_community_route-filter-translated-v4;
                    }
                }                  //flowspec_community_route-filter-translated-v4
                leaf flowspec_community_route-filter-translated-v4_wide {
                    type enumeration {
                        enum flowspec_community_route-filter-translated-v4_wide;
                    }
                }                  //wide
                leaf flowspec_community_exact-match {
                    type enumeration {
                        enum flowspec_community_exact-match;
                    }
                }                  //flowspec_community_exact-match
                leaf flowspec_community_exact-match_wide {
                    type enumeration {
                        enum flowspec_community_exact-match_wide;
                    }
                }                  //wide
                leaf flowspec_community_json {
                    type enumeration {
                        enum flowspec_community_json;
                    }
                }                  //flowspec_community_json
                leaf flowspec_community_json_detail {
                    type enumeration {
                        enum flowspec_community_json_detail;
                    }
                }                  //detail
                leaf flowspec_detail-routes_json {
                    type enumeration {
                        enum flowspec_detail-routes_json;
                    }
                }                  //flowspec_detail-routes_json
                leaf flowspec_detail-routes_json_detail {
                    type enumeration {
                        enum flowspec_detail-routes_json_detail;
                    }
                }                  //detail
                leaf flowspec_summary_established {
                    type enumeration {
                        enum flowspec_summary_established;
                    }
                }                  //flowspec_summary_established
                leaf flowspec_summary_established_neighbor {
                    type enumeration {
                        enum flowspec_summary_established_neighbor;
                    }
                }                  //neighbor
                leaf flowspec_summary_established_remote-as {
                    type enumeration {
                        enum flowspec_summary_established_remote-as;
                    }
                }                  //remote-as
                leaf flowspec_summary_established_json {
                    type enumeration {
                        enum flowspec_summary_established_json;
                    }
                }                  //json
                leaf flowspec_summary_failed {
                    type enumeration {
                        enum flowspec_summary_failed;
                    }
                }                  //flowspec_summary_failed
                leaf flowspec_summary_failed_neighbor {
                    type enumeration {
                        enum flowspec_summary_failed_neighbor;
                    }
                }                  //neighbor
                leaf flowspec_summary_failed_remote-as {
                    type enumeration {
                        enum flowspec_summary_failed_remote-as;
                    }
                }                  //remote-as
                leaf flowspec_summary_failed_json {
                    type enumeration {
                        enum flowspec_summary_failed_json;
                    }
                }                  //json
                leaf flowspec_summary_terse {
                    type enumeration {
                        enum flowspec_summary_terse;
                    }
                }                  //flowspec_summary_terse
                leaf flowspec_summary_terse_json {
                    type enumeration {
                        enum flowspec_summary_terse_json;
                    }
                }                  //json
                leaf flowspec_summary_wide {
                    type enumeration {
                        enum flowspec_summary_wide;
                    }
                }                  //flowspec_summary_wide
                leaf flowspec_summary_wide_json {
                    type enumeration {
                        enum flowspec_summary_wide_json;
                    }
                }                  //json
                leaf vpn_all_cidr-only {
                    type enumeration {
                        enum vpn_all_cidr-only;
                    }
                }                  //vpn_all_cidr-only
                leaf vpn_all_cidr-only_wide {
                    type enumeration {
                        enum vpn_all_cidr-only_wide;
                    }
                }                  //wide
                leaf vpn_all_dampening {
                    type enumeration {
                        enum vpn_all_dampening;
                    }
                }                  //vpn_all_dampening
                leaf vpn_all_community {
                    type enumeration {
                        enum vpn_all_community;
                    }
                }                  //vpn_all_community
                leaf vpn_all_community_wide {
                    type enumeration {
                        enum vpn_all_community_wide;
                    }
                }                  //wide
                leaf vpn_all_detail-routes {
                    type enumeration {
                        enum vpn_all_detail-routes;
                    }
                }                  //vpn_all_detail-routes
                leaf vpn_all_detail-routes_wide {
                    type enumeration {
                        enum vpn_all_detail-routes_wide;
                    }
                }                  //wide
                leaf vpn_all_json {
                    type enumeration {
                        enum vpn_all_json;
                    }
                }                  //vpn_all_json
                leaf vpn_all_json_detail {
                    type enumeration {
                        enum vpn_all_json_detail;
                    }
                }                  //detail
                leaf vpn_all_summary {
                    type enumeration {
                        enum vpn_all_summary;
                    }
                }                  //vpn_all_summary
                leaf vpn_all_summary_neighbor {
                    type enumeration {
                        enum vpn_all_summary_neighbor;
                    }
                }                  //neighbor
                leaf vpn_all_summary_remote-as {
                    type enumeration {
                        enum vpn_all_summary_remote-as;
                    }
                }                  //remote-as
                leaf vpn_all_summary_json {
                    type enumeration {
                        enum vpn_all_summary_json;
                    }
                }                  //json
                leaf vpn_cidr-only_json {
                    type enumeration {
                        enum vpn_cidr-only_json;
                    }
                }                  //vpn_cidr-only_json
                leaf vpn_cidr-only_json_detail {
                    type enumeration {
                        enum vpn_cidr-only_json_detail;
                    }
                }                  //detail
                leaf vpn_dampening_parameters {
                    type enumeration {
                        enum vpn_dampening_parameters;
                    }
                }                  //vpn_dampening_parameters
                leaf vpn_dampening_parameters_json {
                    type enumeration {
                        enum vpn_dampening_parameters_json;
                    }
                }                  //json
                leaf vpn_community_local-AS {
                    type enumeration {
                        enum vpn_community_local-AS;
                    }
                }                  //vpn_community_local-AS
                leaf vpn_community_local-AS_wide {
                    type enumeration {
                        enum vpn_community_local-AS_wide;
                    }
                }                  //wide
                leaf vpn_community_no-advertise {
                    type enumeration {
                        enum vpn_community_no-advertise;
                    }
                }                  //vpn_community_no-advertise
                leaf vpn_community_no-advertise_wide {
                    type enumeration {
                        enum vpn_community_no-advertise_wide;
                    }
                }                  //wide
                leaf vpn_community_no-export {
                    type enumeration {
                        enum vpn_community_no-export;
                    }
                }                  //vpn_community_no-export
                leaf vpn_community_no-export_wide {
                    type enumeration {
                        enum vpn_community_no-export_wide;
                    }
                }                  //wide
                leaf vpn_community_graceful-shutdown {
                    type enumeration {
                        enum vpn_community_graceful-shutdown;
                    }
                }                  //vpn_community_graceful-shutdown
                leaf vpn_community_graceful-shutdown_wide {
                    type enumeration {
                        enum vpn_community_graceful-shutdown_wide;
                    }
                }                  //wide
                leaf vpn_community_no-peer {
                    type enumeration {
                        enum vpn_community_no-peer;
                    }
                }                  //vpn_community_no-peer
                leaf vpn_community_no-peer_wide {
                    type enumeration {
                        enum vpn_community_no-peer_wide;
                    }
                }                  //wide
                leaf vpn_community_blackhole {
                    type enumeration {
                        enum vpn_community_blackhole;
                    }
                }                  //vpn_community_blackhole
                leaf vpn_community_blackhole_wide {
                    type enumeration {
                        enum vpn_community_blackhole_wide;
                    }
                }                  //wide
                leaf vpn_community_llgr-stale {
                    type enumeration {
                        enum vpn_community_llgr-stale;
                    }
                }                  //vpn_community_llgr-stale
                leaf vpn_community_llgr-stale_wide {
                    type enumeration {
                        enum vpn_community_llgr-stale_wide;
                    }
                }                  //wide
                leaf vpn_community_no-llgr {
                    type enumeration {
                        enum vpn_community_no-llgr;
                    }
                }                  //vpn_community_no-llgr
                leaf vpn_community_no-llgr_wide {
                    type enumeration {
                        enum vpn_community_no-llgr_wide;
                    }
                }                  //wide
                leaf vpn_community_accept-own {
                    type enumeration {
                        enum vpn_community_accept-own;
                    }
                }                  //vpn_community_accept-own
                leaf vpn_community_accept-own_wide {
                    type enumeration {
                        enum vpn_community_accept-own_wide;
                    }
                }                  //wide
                leaf vpn_community_accept-own-nexthop {
                    type enumeration {
                        enum vpn_community_accept-own-nexthop;
                    }
                }                  //vpn_community_accept-own-nexthop
                leaf vpn_community_accept-own-nexthop_wide {
                    type enumeration {
                        enum vpn_community_accept-own-nexthop_wide;
                    }
                }                  //wide
                leaf vpn_community_route-filter-v6 {
                    type enumeration {
                        enum vpn_community_route-filter-v6;
                    }
                }                  //vpn_community_route-filter-v6
                leaf vpn_community_route-filter-v6_wide {
                    type enumeration {
                        enum vpn_community_route-filter-v6_wide;
                    }
                }                  //wide
                leaf vpn_community_route-filter-v4 {
                    type enumeration {
                        enum vpn_community_route-filter-v4;
                    }
                }                  //vpn_community_route-filter-v4
                leaf vpn_community_route-filter-v4_wide {
                    type enumeration {
                        enum vpn_community_route-filter-v4_wide;
                    }
                }                  //wide
                leaf vpn_community_route-filter-translated-v6 {
                    type enumeration {
                        enum vpn_community_route-filter-translated-v6;
                    }
                }                  //vpn_community_route-filter-translated-v6
                leaf vpn_community_route-filter-translated-v6_wide {
                    type enumeration {
                        enum vpn_community_route-filter-translated-v6_wide;
                    }
                }                  //wide
                leaf vpn_community_route-filter-translated-v4 {
                    type enumeration {
                        enum vpn_community_route-filter-translated-v4;
                    }
                }                  //vpn_community_route-filter-translated-v4
                leaf vpn_community_route-filter-translated-v4_wide {
                    type enumeration {
                        enum vpn_community_route-filter-translated-v4_wide;
                    }
                }                  //wide
                leaf vpn_community_exact-match {
                    type enumeration {
                        enum vpn_community_exact-match;
                    }
                }                  //vpn_community_exact-match
                leaf vpn_community_exact-match_wide {
                    type enumeration {
                        enum vpn_community_exact-match_wide;
                    }
                }                  //wide
                leaf vpn_community_json {
                    type enumeration {
                        enum vpn_community_json;
                    }
                }                  //vpn_community_json
                leaf vpn_community_json_detail {
                    type enumeration {
                        enum vpn_community_json_detail;
                    }
                }                  //detail
                leaf vpn_detail-routes_json {
                    type enumeration {
                        enum vpn_detail-routes_json;
                    }
                }                  //vpn_detail-routes_json
                leaf vpn_detail-routes_json_detail {
                    type enumeration {
                        enum vpn_detail-routes_json_detail;
                    }
                }                  //detail
                leaf vpn_summary_established {
                    type enumeration {
                        enum vpn_summary_established;
                    }
                }                  //vpn_summary_established
                leaf vpn_summary_established_neighbor {
                    type enumeration {
                        enum vpn_summary_established_neighbor;
                    }
                }                  //neighbor
                leaf vpn_summary_established_remote-as {
                    type enumeration {
                        enum vpn_summary_established_remote-as;
                    }
                }                  //remote-as
                leaf vpn_summary_established_json {
                    type enumeration {
                        enum vpn_summary_established_json;
                    }
                }                  //json
                leaf vpn_summary_failed {
                    type enumeration {
                        enum vpn_summary_failed;
                    }
                }                  //vpn_summary_failed
                leaf vpn_summary_failed_neighbor {
                    type enumeration {
                        enum vpn_summary_failed_neighbor;
                    }
                }                  //neighbor
                leaf vpn_summary_failed_remote-as {
                    type enumeration {
                        enum vpn_summary_failed_remote-as;
                    }
                }                  //remote-as
                leaf vpn_summary_failed_json {
                    type enumeration {
                        enum vpn_summary_failed_json;
                    }
                }                  //json
                leaf vpn_summary_terse {
                    type enumeration {
                        enum vpn_summary_terse;
                    }
                }                  //vpn_summary_terse
                leaf vpn_summary_terse_json {
                    type enumeration {
                        enum vpn_summary_terse_json;
                    }
                }                  //json
                leaf vpn_summary_wide {
                    type enumeration {
                        enum vpn_summary_wide;
                    }
                }                  //vpn_summary_wide
                leaf vpn_summary_wide_json {
                    type enumeration {
                        enum vpn_summary_wide_json;
                    }
                }                  //json
                leaf unicast_all_cidr-only_json {
                    type enumeration {
                        enum unicast_all_cidr-only_json;
                    }
                }                  //unicast_all_cidr-only_json
                leaf unicast_all_cidr-only_json_detail {
                    type enumeration {
                        enum unicast_all_cidr-only_json_detail;
                    }
                }                  //detail
                leaf unicast_all_dampening_parameters {
                    type enumeration {
                        enum unicast_all_dampening_parameters;
                    }
                }                  //unicast_all_dampening_parameters
                leaf unicast_all_dampening_parameters_json {
                    type enumeration {
                        enum unicast_all_dampening_parameters_json;
                    }
                }                  //json
                leaf unicast_all_community_local-AS {
                    type enumeration {
                        enum unicast_all_community_local-AS;
                    }
                }                  //unicast_all_community_local-AS
                leaf unicast_all_community_local-AS_wide {
                    type enumeration {
                        enum unicast_all_community_local-AS_wide;
                    }
                }                  //wide
                leaf unicast_all_community_no-advertise {
                    type enumeration {
                        enum unicast_all_community_no-advertise;
                    }
                }                  //unicast_all_community_no-advertise
                leaf unicast_all_community_no-advertise_wide {
                    type enumeration {
                        enum unicast_all_community_no-advertise_wide;
                    }
                }                  //wide
                leaf unicast_all_community_no-export {
                    type enumeration {
                        enum unicast_all_community_no-export;
                    }
                }                  //unicast_all_community_no-export
                leaf unicast_all_community_no-export_wide {
                    type enumeration {
                        enum unicast_all_community_no-export_wide;
                    }
                }                  //wide
                leaf unicast_all_community_graceful-shutdown {
                    type enumeration {
                        enum unicast_all_community_graceful-shutdown;
                    }
                }                  //unicast_all_community_graceful-shutdown
                leaf unicast_all_community_graceful-shutdown_wide {
                    type enumeration {
                        enum unicast_all_community_graceful-shutdown_wide;
                    }
                }                  //wide
                leaf unicast_all_community_no-peer {
                    type enumeration {
                        enum unicast_all_community_no-peer;
                    }
                }                  //unicast_all_community_no-peer
                leaf unicast_all_community_no-peer_wide {
                    type enumeration {
                        enum unicast_all_community_no-peer_wide;
                    }
                }                  //wide
                leaf unicast_all_community_blackhole {
                    type enumeration {
                        enum unicast_all_community_blackhole;
                    }
                }                  //unicast_all_community_blackhole
                leaf unicast_all_community_blackhole_wide {
                    type enumeration {
                        enum unicast_all_community_blackhole_wide;
                    }
                }                  //wide
                leaf unicast_all_community_llgr-stale {
                    type enumeration {
                        enum unicast_all_community_llgr-stale;
                    }
                }                  //unicast_all_community_llgr-stale
                leaf unicast_all_community_llgr-stale_wide {
                    type enumeration {
                        enum unicast_all_community_llgr-stale_wide;
                    }
                }                  //wide
                leaf unicast_all_community_no-llgr {
                    type enumeration {
                        enum unicast_all_community_no-llgr;
                    }
                }                  //unicast_all_community_no-llgr
                leaf unicast_all_community_no-llgr_wide {
                    type enumeration {
                        enum unicast_all_community_no-llgr_wide;
                    }
                }                  //wide
                leaf unicast_all_community_accept-own {
                    type enumeration {
                        enum unicast_all_community_accept-own;
                    }
                }                  //unicast_all_community_accept-own
                leaf unicast_all_community_accept-own_wide {
                    type enumeration {
                        enum unicast_all_community_accept-own_wide;
                    }
                }                  //wide
                leaf unicast_all_community_accept-own-nexthop {
                    type enumeration {
                        enum unicast_all_community_accept-own-nexthop;
                    }
                }                  //unicast_all_community_accept-own-nexthop
                leaf unicast_all_community_accept-own-nexthop_wide {
                    type enumeration {
                        enum unicast_all_community_accept-own-nexthop_wide;
                    }
                }                  //wide
                leaf unicast_all_community_route-filter-v6 {
                    type enumeration {
                        enum unicast_all_community_route-filter-v6;
                    }
                }                  //unicast_all_community_route-filter-v6
                leaf unicast_all_community_route-filter-v6_wide {
                    type enumeration {
                        enum unicast_all_community_route-filter-v6_wide;
                    }
                }                  //wide
                leaf unicast_all_community_route-filter-v4 {
                    type enumeration {
                        enum unicast_all_community_route-filter-v4;
                    }
                }                  //unicast_all_community_route-filter-v4
                leaf unicast_all_community_route-filter-v4_wide {
                    type enumeration {
                        enum unicast_all_community_route-filter-v4_wide;
                    }
                }                  //wide
                leaf unicast_all_community_route-filter-translated-v6 {
                    type enumeration {
                        enum unicast_all_community_route-filter-translated-v6;
                    }
                }                  //unicast_all_community_route-filter-translated-v6
                leaf unicast_all_community_route-filter-translated-v6_wide {
                    type enumeration {
                        enum unicast_all_community_route-filter-translated-v6_wide;
                    }
                }                  //wide
                leaf unicast_all_community_route-filter-translated-v4 {
                    type enumeration {
                        enum unicast_all_community_route-filter-translated-v4;
                    }
                }                  //unicast_all_community_route-filter-translated-v4
                leaf unicast_all_community_route-filter-translated-v4_wide {
                    type enumeration {
                        enum unicast_all_community_route-filter-translated-v4_wide;
                    }
                }                  //wide
                leaf unicast_all_community_exact-match {
                    type enumeration {
                        enum unicast_all_community_exact-match;
                    }
                }                  //unicast_all_community_exact-match
                leaf unicast_all_community_exact-match_wide {
                    type enumeration {
                        enum unicast_all_community_exact-match_wide;
                    }
                }                  //wide
                leaf unicast_all_community_json {
                    type enumeration {
                        enum unicast_all_community_json;
                    }
                }                  //unicast_all_community_json
                leaf unicast_all_community_json_detail {
                    type enumeration {
                        enum unicast_all_community_json_detail;
                    }
                }                  //detail
                leaf unicast_all_detail-routes_json {
                    type enumeration {
                        enum unicast_all_detail-routes_json;
                    }
                }                  //unicast_all_detail-routes_json
                leaf unicast_all_detail-routes_json_detail {
                    type enumeration {
                        enum unicast_all_detail-routes_json_detail;
                    }
                }                  //detail
                leaf unicast_all_summary_established {
                    type enumeration {
                        enum unicast_all_summary_established;
                    }
                }                  //unicast_all_summary_established
                leaf unicast_all_summary_established_neighbor {
                    type enumeration {
                        enum unicast_all_summary_established_neighbor;
                    }
                }                  //neighbor
                leaf unicast_all_summary_established_remote-as {
                    type enumeration {
                        enum unicast_all_summary_established_remote-as;
                    }
                }                  //remote-as
                leaf unicast_all_summary_established_json {
                    type enumeration {
                        enum unicast_all_summary_established_json;
                    }
                }                  //json
                leaf unicast_all_summary_failed {
                    type enumeration {
                        enum unicast_all_summary_failed;
                    }
                }                  //unicast_all_summary_failed
                leaf unicast_all_summary_failed_neighbor {
                    type enumeration {
                        enum unicast_all_summary_failed_neighbor;
                    }
                }                  //neighbor
                leaf unicast_all_summary_failed_remote-as {
                    type enumeration {
                        enum unicast_all_summary_failed_remote-as;
                    }
                }                  //remote-as
                leaf unicast_all_summary_failed_json {
                    type enumeration {
                        enum unicast_all_summary_failed_json;
                    }
                }                  //json
                leaf unicast_all_summary_terse {
                    type enumeration {
                        enum unicast_all_summary_terse;
                    }
                }                  //unicast_all_summary_terse
                leaf unicast_all_summary_terse_json {
                    type enumeration {
                        enum unicast_all_summary_terse_json;
                    }
                }                  //json
                leaf unicast_all_summary_wide {
                    type enumeration {
                        enum unicast_all_summary_wide;
                    }
                }                  //unicast_all_summary_wide
                leaf unicast_all_summary_wide_json {
                    type enumeration {
                        enum unicast_all_summary_wide_json;
                    }
                }                  //json
                leaf unicast_community_local-AS_exact-match {
                    type enumeration {
                        enum unicast_community_local-AS_exact-match;
                    }
                }                  //unicast_community_local-AS_exact-match
                leaf unicast_community_local-AS_exact-match_wide {
                    type enumeration {
                        enum unicast_community_local-AS_exact-match_wide;
                    }
                }                  //wide
                leaf unicast_community_local-AS_json {
                    type enumeration {
                        enum unicast_community_local-AS_json;
                    }
                }                  //unicast_community_local-AS_json
                leaf unicast_community_local-AS_json_detail {
                    type enumeration {
                        enum unicast_community_local-AS_json_detail;
                    }
                }                  //detail
                leaf unicast_community_no-advertise_exact-match {
                    type enumeration {
                        enum unicast_community_no-advertise_exact-match;
                    }
                }                  //unicast_community_no-advertise_exact-match
                leaf unicast_community_no-advertise_exact-match_wide {
                    type enumeration {
                        enum unicast_community_no-advertise_exact-match_wide;
                    }
                }                  //wide
                leaf unicast_community_no-advertise_json {
                    type enumeration {
                        enum unicast_community_no-advertise_json;
                    }
                }                  //unicast_community_no-advertise_json
                leaf unicast_community_no-advertise_json_detail {
                    type enumeration {
                        enum unicast_community_no-advertise_json_detail;
                    }
                }                  //detail
                leaf unicast_community_no-export_exact-match {
                    type enumeration {
                        enum unicast_community_no-export_exact-match;
                    }
                }                  //unicast_community_no-export_exact-match
                leaf unicast_community_no-export_exact-match_wide {
                    type enumeration {
                        enum unicast_community_no-export_exact-match_wide;
                    }
                }                  //wide
                leaf unicast_community_no-export_json {
                    type enumeration {
                        enum unicast_community_no-export_json;
                    }
                }                  //unicast_community_no-export_json
                leaf unicast_community_no-export_json_detail {
                    type enumeration {
                        enum unicast_community_no-export_json_detail;
                    }
                }                  //detail
                leaf unicast_community_graceful-shutdown_exact-match {
                    type enumeration {
                        enum unicast_community_graceful-shutdown_exact-match;
                    }
                }                  //unicast_community_graceful-shutdown_exact-match
                leaf unicast_community_graceful-shutdown_exact-match_wide {
                    type enumeration {
                        enum unicast_community_graceful-shutdown_exact-match_wide;
                    }
                }                  //wide
                leaf unicast_community_graceful-shutdown_json {
                    type enumeration {
                        enum unicast_community_graceful-shutdown_json;
                    }
                }                  //unicast_community_graceful-shutdown_json
                leaf unicast_community_graceful-shutdown_json_detail {
                    type enumeration {
                        enum unicast_community_graceful-shutdown_json_detail;
                    }
                }                  //detail
                leaf unicast_community_no-peer_exact-match {
                    type enumeration {
                        enum unicast_community_no-peer_exact-match;
                    }
                }                  //unicast_community_no-peer_exact-match
                leaf unicast_community_no-peer_exact-match_wide {
                    type enumeration {
                        enum unicast_community_no-peer_exact-match_wide;
                    }
                }                  //wide
                leaf unicast_community_no-peer_json {
                    type enumeration {
                        enum unicast_community_no-peer_json;
                    }
                }                  //unicast_community_no-peer_json
                leaf unicast_community_no-peer_json_detail {
                    type enumeration {
                        enum unicast_community_no-peer_json_detail;
                    }
                }                  //detail
                leaf unicast_community_blackhole_exact-match {
                    type enumeration {
                        enum unicast_community_blackhole_exact-match;
                    }
                }                  //unicast_community_blackhole_exact-match
                leaf unicast_community_blackhole_exact-match_wide {
                    type enumeration {
                        enum unicast_community_blackhole_exact-match_wide;
                    }
                }                  //wide
                leaf unicast_community_blackhole_json {
                    type enumeration {
                        enum unicast_community_blackhole_json;
                    }
                }                  //unicast_community_blackhole_json
                leaf unicast_community_blackhole_json_detail {
                    type enumeration {
                        enum unicast_community_blackhole_json_detail;
                    }
                }                  //detail
                leaf unicast_community_llgr-stale_exact-match {
                    type enumeration {
                        enum unicast_community_llgr-stale_exact-match;
                    }
                }                  //unicast_community_llgr-stale_exact-match
                leaf unicast_community_llgr-stale_exact-match_wide {
                    type enumeration {
                        enum unicast_community_llgr-stale_exact-match_wide;
                    }
                }                  //wide
                leaf unicast_community_llgr-stale_json {
                    type enumeration {
                        enum unicast_community_llgr-stale_json;
                    }
                }                  //unicast_community_llgr-stale_json
                leaf unicast_community_llgr-stale_json_detail {
                    type enumeration {
                        enum unicast_community_llgr-stale_json_detail;
                    }
                }                  //detail
                leaf unicast_community_no-llgr_exact-match {
                    type enumeration {
                        enum unicast_community_no-llgr_exact-match;
                    }
                }                  //unicast_community_no-llgr_exact-match
                leaf unicast_community_no-llgr_exact-match_wide {
                    type enumeration {
                        enum unicast_community_no-llgr_exact-match_wide;
                    }
                }                  //wide
                leaf unicast_community_no-llgr_json {
                    type enumeration {
                        enum unicast_community_no-llgr_json;
                    }
                }                  //unicast_community_no-llgr_json
                leaf unicast_community_no-llgr_json_detail {
                    type enumeration {
                        enum unicast_community_no-llgr_json_detail;
                    }
                }                  //detail
                leaf unicast_community_accept-own_exact-match {
                    type enumeration {
                        enum unicast_community_accept-own_exact-match;
                    }
                }                  //unicast_community_accept-own_exact-match
                leaf unicast_community_accept-own_exact-match_wide {
                    type enumeration {
                        enum unicast_community_accept-own_exact-match_wide;
                    }
                }                  //wide
                leaf unicast_community_accept-own_json {
                    type enumeration {
                        enum unicast_community_accept-own_json;
                    }
                }                  //unicast_community_accept-own_json
                leaf unicast_community_accept-own_json_detail {
                    type enumeration {
                        enum unicast_community_accept-own_json_detail;
                    }
                }                  //detail
                leaf unicast_community_accept-own-nexthop_exact-match {
                    type enumeration {
                        enum unicast_community_accept-own-nexthop_exact-match;
                    }
                }                  //unicast_community_accept-own-nexthop_exact-match
                leaf unicast_community_accept-own-nexthop_exact-match_wide {
                    type enumeration {
                        enum unicast_community_accept-own-nexthop_exact-match_wide;
                    }
                }                  //wide
                leaf unicast_community_accept-own-nexthop_json {
                    type enumeration {
                        enum unicast_community_accept-own-nexthop_json;
                    }
                }                  //unicast_community_accept-own-nexthop_json
                leaf unicast_community_accept-own-nexthop_json_detail {
                    type enumeration {
                        enum unicast_community_accept-own-nexthop_json_detail;
                    }
                }                  //detail
                leaf unicast_community_route-filter-v6_exact-match {
                    type enumeration {
                        enum unicast_community_route-filter-v6_exact-match;
                    }
                }                  //unicast_community_route-filter-v6_exact-match
                leaf unicast_community_route-filter-v6_exact-match_wide {
                    type enumeration {
                        enum unicast_community_route-filter-v6_exact-match_wide;
                    }
                }                  //wide
                leaf unicast_community_route-filter-v6_json {
                    type enumeration {
                        enum unicast_community_route-filter-v6_json;
                    }
                }                  //unicast_community_route-filter-v6_json
                leaf unicast_community_route-filter-v6_json_detail {
                    type enumeration {
                        enum unicast_community_route-filter-v6_json_detail;
                    }
                }                  //detail
                leaf unicast_community_route-filter-v4_exact-match {
                    type enumeration {
                        enum unicast_community_route-filter-v4_exact-match;
                    }
                }                  //unicast_community_route-filter-v4_exact-match
                leaf unicast_community_route-filter-v4_exact-match_wide {
                    type enumeration {
                        enum unicast_community_route-filter-v4_exact-match_wide;
                    }
                }                  //wide
                leaf unicast_community_route-filter-v4_json {
                    type enumeration {
                        enum unicast_community_route-filter-v4_json;
                    }
                }                  //unicast_community_route-filter-v4_json
                leaf unicast_community_route-filter-v4_json_detail {
                    type enumeration {
                        enum unicast_community_route-filter-v4_json_detail;
                    }
                }                  //detail
                leaf unicast_community_route-filter-translated-v6_exact-match {
                    type enumeration {
                        enum unicast_community_route-filter-translated-v6_exact-match;
                    }
                }                  //unicast_community_route-filter-translated-v6_exact-match
                leaf unicast_community_route-filter-translated-v6_exact-match_wide {
                    type enumeration {
                        enum unicast_community_route-filter-translated-v6_exact-match_wide;
                    }
                }                  //wide
                leaf unicast_community_route-filter-translated-v6_json {
                    type enumeration {
                        enum unicast_community_route-filter-translated-v6_json;
                    }
                }                  //unicast_community_route-filter-translated-v6_json
                leaf unicast_community_route-filter-translated-v6_json_detail {
                    type enumeration {
                        enum unicast_community_route-filter-translated-v6_json_detail;
                    }
                }                  //detail
                leaf unicast_community_route-filter-translated-v4_exact-match {
                    type enumeration {
                        enum unicast_community_route-filter-translated-v4_exact-match;
                    }
                }                  //unicast_community_route-filter-translated-v4_exact-match
                leaf unicast_community_route-filter-translated-v4_exact-match_wide {
                    type enumeration {
                        enum unicast_community_route-filter-translated-v4_exact-match_wide;
                    }
                }                  //wide
                leaf unicast_community_route-filter-translated-v4_json {
                    type enumeration {
                        enum unicast_community_route-filter-translated-v4_json;
                    }
                }                  //unicast_community_route-filter-translated-v4_json
                leaf unicast_community_route-filter-translated-v4_json_detail {
                    type enumeration {
                        enum unicast_community_route-filter-translated-v4_json_detail;
                    }
                }                  //detail
                leaf unicast_community_exact-match_json {
                    type enumeration {
                        enum unicast_community_exact-match_json;
                    }
                }                  //unicast_community_exact-match_json
                leaf unicast_community_exact-match_json_detail {
                    type enumeration {
                        enum unicast_community_exact-match_json_detail;
                    }
                }                  //detail
                leaf unicast_summary_established_terse {
                    type enumeration {
                        enum unicast_summary_established_terse;
                    }
                }                  //unicast_summary_established_terse
                leaf unicast_summary_established_terse_json {
                    type enumeration {
                        enum unicast_summary_established_terse_json;
                    }
                }                  //json
                leaf unicast_summary_established_wide {
                    type enumeration {
                        enum unicast_summary_established_wide;
                    }
                }                  //unicast_summary_established_wide
                leaf unicast_summary_established_wide_json {
                    type enumeration {
                        enum unicast_summary_established_wide_json;
                    }
                }                  //json
                leaf unicast_summary_failed_terse {
                    type enumeration {
                        enum unicast_summary_failed_terse;
                    }
                }                  //unicast_summary_failed_terse
                leaf unicast_summary_failed_terse_json {
                    type enumeration {
                        enum unicast_summary_failed_terse_json;
                    }
                }                  //json
                leaf unicast_summary_failed_wide {
                    type enumeration {
                        enum unicast_summary_failed_wide;
                    }
                }                  //unicast_summary_failed_wide
                leaf unicast_summary_failed_wide_json {
                    type enumeration {
                        enum unicast_summary_failed_wide_json;
                    }
                }                  //json
                leaf unicast_summary_terse_wide {
                    type enumeration {
                        enum unicast_summary_terse_wide;
                    }
                }                  //unicast_summary_terse_wide
                leaf unicast_summary_terse_wide_json {
                    type enumeration {
                        enum unicast_summary_terse_wide_json;
                    }
                }                  //json
                leaf flowspec_all_cidr-only_json {
                    type enumeration {
                        enum flowspec_all_cidr-only_json;
                    }
                }                  //flowspec_all_cidr-only_json
                leaf flowspec_all_cidr-only_json_detail {
                    type enumeration {
                        enum flowspec_all_cidr-only_json_detail;
                    }
                }                  //detail
                leaf flowspec_all_dampening_parameters {
                    type enumeration {
                        enum flowspec_all_dampening_parameters;
                    }
                }                  //flowspec_all_dampening_parameters
                leaf flowspec_all_dampening_parameters_json {
                    type enumeration {
                        enum flowspec_all_dampening_parameters_json;
                    }
                }                  //json
                leaf flowspec_all_community_local-AS {
                    type enumeration {
                        enum flowspec_all_community_local-AS;
                    }
                }                  //flowspec_all_community_local-AS
                leaf flowspec_all_community_local-AS_wide {
                    type enumeration {
                        enum flowspec_all_community_local-AS_wide;
                    }
                }                  //wide
                leaf flowspec_all_community_no-advertise {
                    type enumeration {
                        enum flowspec_all_community_no-advertise;
                    }
                }                  //flowspec_all_community_no-advertise
                leaf flowspec_all_community_no-advertise_wide {
                    type enumeration {
                        enum flowspec_all_community_no-advertise_wide;
                    }
                }                  //wide
                leaf flowspec_all_community_no-export {
                    type enumeration {
                        enum flowspec_all_community_no-export;
                    }
                }                  //flowspec_all_community_no-export
                leaf flowspec_all_community_no-export_wide {
                    type enumeration {
                        enum flowspec_all_community_no-export_wide;
                    }
                }                  //wide
                leaf flowspec_all_community_graceful-shutdown {
                    type enumeration {
                        enum flowspec_all_community_graceful-shutdown;
                    }
                }                  //flowspec_all_community_graceful-shutdown
                leaf flowspec_all_community_graceful-shutdown_wide {
                    type enumeration {
                        enum flowspec_all_community_graceful-shutdown_wide;
                    }
                }                  //wide
                leaf flowspec_all_community_no-peer {
                    type enumeration {
                        enum flowspec_all_community_no-peer;
                    }
                }                  //flowspec_all_community_no-peer
                leaf flowspec_all_community_no-peer_wide {
                    type enumeration {
                        enum flowspec_all_community_no-peer_wide;
                    }
                }                  //wide
                leaf flowspec_all_community_blackhole {
                    type enumeration {
                        enum flowspec_all_community_blackhole;
                    }
                }                  //flowspec_all_community_blackhole
                leaf flowspec_all_community_blackhole_wide {
                    type enumeration {
                        enum flowspec_all_community_blackhole_wide;
                    }
                }                  //wide
                leaf flowspec_all_community_llgr-stale {
                    type enumeration {
                        enum flowspec_all_community_llgr-stale;
                    }
                }                  //flowspec_all_community_llgr-stale
                leaf flowspec_all_community_llgr-stale_wide {
                    type enumeration {
                        enum flowspec_all_community_llgr-stale_wide;
                    }
                }                  //wide
                leaf flowspec_all_community_no-llgr {
                    type enumeration {
                        enum flowspec_all_community_no-llgr;
                    }
                }                  //flowspec_all_community_no-llgr
                leaf flowspec_all_community_no-llgr_wide {
                    type enumeration {
                        enum flowspec_all_community_no-llgr_wide;
                    }
                }                  //wide
                leaf flowspec_all_community_accept-own {
                    type enumeration {
                        enum flowspec_all_community_accept-own;
                    }
                }                  //flowspec_all_community_accept-own
                leaf flowspec_all_community_accept-own_wide {
                    type enumeration {
                        enum flowspec_all_community_accept-own_wide;
                    }
                }                  //wide
                leaf flowspec_all_community_accept-own-nexthop {
                    type enumeration {
                        enum flowspec_all_community_accept-own-nexthop;
                    }
                }                  //flowspec_all_community_accept-own-nexthop
                leaf flowspec_all_community_accept-own-nexthop_wide {
                    type enumeration {
                        enum flowspec_all_community_accept-own-nexthop_wide;
                    }
                }                  //wide
                leaf flowspec_all_community_route-filter-v6 {
                    type enumeration {
                        enum flowspec_all_community_route-filter-v6;
                    }
                }                  //flowspec_all_community_route-filter-v6
                leaf flowspec_all_community_route-filter-v6_wide {
                    type enumeration {
                        enum flowspec_all_community_route-filter-v6_wide;
                    }
                }                  //wide
                leaf flowspec_all_community_route-filter-v4 {
                    type enumeration {
                        enum flowspec_all_community_route-filter-v4;
                    }
                }                  //flowspec_all_community_route-filter-v4
                leaf flowspec_all_community_route-filter-v4_wide {
                    type enumeration {
                        enum flowspec_all_community_route-filter-v4_wide;
                    }
                }                  //wide
                leaf flowspec_all_community_route-filter-translated-v6 {
                    type enumeration {
                        enum flowspec_all_community_route-filter-translated-v6;
                    }
                }                  //flowspec_all_community_route-filter-translated-v6
                leaf flowspec_all_community_route-filter-translated-v6_wide {
                    type enumeration {
                        enum flowspec_all_community_route-filter-translated-v6_wide;
                    }
                }                  //wide
                leaf flowspec_all_community_route-filter-translated-v4 {
                    type enumeration {
                        enum flowspec_all_community_route-filter-translated-v4;
                    }
                }                  //flowspec_all_community_route-filter-translated-v4
                leaf flowspec_all_community_route-filter-translated-v4_wide {
                    type enumeration {
                        enum flowspec_all_community_route-filter-translated-v4_wide;
                    }
                }                  //wide
                leaf flowspec_all_community_exact-match {
                    type enumeration {
                        enum flowspec_all_community_exact-match;
                    }
                }                  //flowspec_all_community_exact-match
                leaf flowspec_all_community_exact-match_wide {
                    type enumeration {
                        enum flowspec_all_community_exact-match_wide;
                    }
                }                  //wide
                leaf flowspec_all_community_json {
                    type enumeration {
                        enum flowspec_all_community_json;
                    }
                }                  //flowspec_all_community_json
                leaf flowspec_all_community_json_detail {
                    type enumeration {
                        enum flowspec_all_community_json_detail;
                    }
                }                  //detail
                leaf flowspec_all_detail-routes_json {
                    type enumeration {
                        enum flowspec_all_detail-routes_json;
                    }
                }                  //flowspec_all_detail-routes_json
                leaf flowspec_all_detail-routes_json_detail {
                    type enumeration {
                        enum flowspec_all_detail-routes_json_detail;
                    }
                }                  //detail
                leaf flowspec_all_summary_established {
                    type enumeration {
                        enum flowspec_all_summary_established;
                    }
                }                  //flowspec_all_summary_established
                leaf flowspec_all_summary_established_neighbor {
                    type enumeration {
                        enum flowspec_all_summary_established_neighbor;
                    }
                }                  //neighbor
                leaf flowspec_all_summary_established_remote-as {
                    type enumeration {
                        enum flowspec_all_summary_established_remote-as;
                    }
                }                  //remote-as
                leaf flowspec_all_summary_established_json {
                    type enumeration {
                        enum flowspec_all_summary_established_json;
                    }
                }                  //json
                leaf flowspec_all_summary_failed {
                    type enumeration {
                        enum flowspec_all_summary_failed;
                    }
                }                  //flowspec_all_summary_failed
                leaf flowspec_all_summary_failed_neighbor {
                    type enumeration {
                        enum flowspec_all_summary_failed_neighbor;
                    }
                }                  //neighbor
                leaf flowspec_all_summary_failed_remote-as {
                    type enumeration {
                        enum flowspec_all_summary_failed_remote-as;
                    }
                }                  //remote-as
                leaf flowspec_all_summary_failed_json {
                    type enumeration {
                        enum flowspec_all_summary_failed_json;
                    }
                }                  //json
                leaf flowspec_all_summary_terse {
                    type enumeration {
                        enum flowspec_all_summary_terse;
                    }
                }                  //flowspec_all_summary_terse
                leaf flowspec_all_summary_terse_json {
                    type enumeration {
                        enum flowspec_all_summary_terse_json;
                    }
                }                  //json
                leaf flowspec_all_summary_wide {
                    type enumeration {
                        enum flowspec_all_summary_wide;
                    }
                }                  //flowspec_all_summary_wide
                leaf flowspec_all_summary_wide_json {
                    type enumeration {
                        enum flowspec_all_summary_wide_json;
                    }
                }                  //json
                leaf flowspec_community_local-AS_exact-match {
                    type enumeration {
                        enum flowspec_community_local-AS_exact-match;
                    }
                }                  //flowspec_community_local-AS_exact-match
                leaf flowspec_community_local-AS_exact-match_wide {
                    type enumeration {
                        enum flowspec_community_local-AS_exact-match_wide;
                    }
                }                  //wide
                leaf flowspec_community_local-AS_json {
                    type enumeration {
                        enum flowspec_community_local-AS_json;
                    }
                }                  //flowspec_community_local-AS_json
                leaf flowspec_community_local-AS_json_detail {
                    type enumeration {
                        enum flowspec_community_local-AS_json_detail;
                    }
                }                  //detail
                leaf flowspec_community_no-advertise_exact-match {
                    type enumeration {
                        enum flowspec_community_no-advertise_exact-match;
                    }
                }                  //flowspec_community_no-advertise_exact-match
                leaf flowspec_community_no-advertise_exact-match_wide {
                    type enumeration {
                        enum flowspec_community_no-advertise_exact-match_wide;
                    }
                }                  //wide
                leaf flowspec_community_no-advertise_json {
                    type enumeration {
                        enum flowspec_community_no-advertise_json;
                    }
                }                  //flowspec_community_no-advertise_json
                leaf flowspec_community_no-advertise_json_detail {
                    type enumeration {
                        enum flowspec_community_no-advertise_json_detail;
                    }
                }                  //detail
                leaf flowspec_community_no-export_exact-match {
                    type enumeration {
                        enum flowspec_community_no-export_exact-match;
                    }
                }                  //flowspec_community_no-export_exact-match
                leaf flowspec_community_no-export_exact-match_wide {
                    type enumeration {
                        enum flowspec_community_no-export_exact-match_wide;
                    }
                }                  //wide
                leaf flowspec_community_no-export_json {
                    type enumeration {
                        enum flowspec_community_no-export_json;
                    }
                }                  //flowspec_community_no-export_json
                leaf flowspec_community_no-export_json_detail {
                    type enumeration {
                        enum flowspec_community_no-export_json_detail;
                    }
                }                  //detail
                leaf flowspec_community_graceful-shutdown_exact-match {
                    type enumeration {
                        enum flowspec_community_graceful-shutdown_exact-match;
                    }
                }                  //flowspec_community_graceful-shutdown_exact-match
                leaf flowspec_community_graceful-shutdown_exact-match_wide {
                    type enumeration {
                        enum flowspec_community_graceful-shutdown_exact-match_wide;
                    }
                }                  //wide
                leaf flowspec_community_graceful-shutdown_json {
                    type enumeration {
                        enum flowspec_community_graceful-shutdown_json;
                    }
                }                  //flowspec_community_graceful-shutdown_json
                leaf flowspec_community_graceful-shutdown_json_detail {
                    type enumeration {
                        enum flowspec_community_graceful-shutdown_json_detail;
                    }
                }                  //detail
                leaf flowspec_community_no-peer_exact-match {
                    type enumeration {
                        enum flowspec_community_no-peer_exact-match;
                    }
                }                  //flowspec_community_no-peer_exact-match
                leaf flowspec_community_no-peer_exact-match_wide {
                    type enumeration {
                        enum flowspec_community_no-peer_exact-match_wide;
                    }
                }                  //wide
                leaf flowspec_community_no-peer_json {
                    type enumeration {
                        enum flowspec_community_no-peer_json;
                    }
                }                  //flowspec_community_no-peer_json
                leaf flowspec_community_no-peer_json_detail {
                    type enumeration {
                        enum flowspec_community_no-peer_json_detail;
                    }
                }                  //detail
                leaf flowspec_community_blackhole_exact-match {
                    type enumeration {
                        enum flowspec_community_blackhole_exact-match;
                    }
                }                  //flowspec_community_blackhole_exact-match
                leaf flowspec_community_blackhole_exact-match_wide {
                    type enumeration {
                        enum flowspec_community_blackhole_exact-match_wide;
                    }
                }                  //wide
                leaf flowspec_community_blackhole_json {
                    type enumeration {
                        enum flowspec_community_blackhole_json;
                    }
                }                  //flowspec_community_blackhole_json
                leaf flowspec_community_blackhole_json_detail {
                    type enumeration {
                        enum flowspec_community_blackhole_json_detail;
                    }
                }                  //detail
                leaf flowspec_community_llgr-stale_exact-match {
                    type enumeration {
                        enum flowspec_community_llgr-stale_exact-match;
                    }
                }                  //flowspec_community_llgr-stale_exact-match
                leaf flowspec_community_llgr-stale_exact-match_wide {
                    type enumeration {
                        enum flowspec_community_llgr-stale_exact-match_wide;
                    }
                }                  //wide
                leaf flowspec_community_llgr-stale_json {
                    type enumeration {
                        enum flowspec_community_llgr-stale_json;
                    }
                }                  //flowspec_community_llgr-stale_json
                leaf flowspec_community_llgr-stale_json_detail {
                    type enumeration {
                        enum flowspec_community_llgr-stale_json_detail;
                    }
                }                  //detail
                leaf flowspec_community_no-llgr_exact-match {
                    type enumeration {
                        enum flowspec_community_no-llgr_exact-match;
                    }
                }                  //flowspec_community_no-llgr_exact-match
                leaf flowspec_community_no-llgr_exact-match_wide {
                    type enumeration {
                        enum flowspec_community_no-llgr_exact-match_wide;
                    }
                }                  //wide
                leaf flowspec_community_no-llgr_json {
                    type enumeration {
                        enum flowspec_community_no-llgr_json;
                    }
                }                  //flowspec_community_no-llgr_json
                leaf flowspec_community_no-llgr_json_detail {
                    type enumeration {
                        enum flowspec_community_no-llgr_json_detail;
                    }
                }                  //detail
                leaf flowspec_community_accept-own_exact-match {
                    type enumeration {
                        enum flowspec_community_accept-own_exact-match;
                    }
                }                  //flowspec_community_accept-own_exact-match
                leaf flowspec_community_accept-own_exact-match_wide {
                    type enumeration {
                        enum flowspec_community_accept-own_exact-match_wide;
                    }
                }                  //wide
                leaf flowspec_community_accept-own_json {
                    type enumeration {
                        enum flowspec_community_accept-own_json;
                    }
                }                  //flowspec_community_accept-own_json
                leaf flowspec_community_accept-own_json_detail {
                    type enumeration {
                        enum flowspec_community_accept-own_json_detail;
                    }
                }                  //detail
                leaf flowspec_community_accept-own-nexthop_exact-match {
                    type enumeration {
                        enum flowspec_community_accept-own-nexthop_exact-match;
                    }
                }                  //flowspec_community_accept-own-nexthop_exact-match
                leaf flowspec_community_accept-own-nexthop_exact-match_wide {
                    type enumeration {
                        enum flowspec_community_accept-own-nexthop_exact-match_wide;
                    }
                }                  //wide
                leaf flowspec_community_accept-own-nexthop_json {
                    type enumeration {
                        enum flowspec_community_accept-own-nexthop_json;
                    }
                }                  //flowspec_community_accept-own-nexthop_json
                leaf flowspec_community_accept-own-nexthop_json_detail {
                    type enumeration {
                        enum flowspec_community_accept-own-nexthop_json_detail;
                    }
                }                  //detail
                leaf flowspec_community_route-filter-v6_exact-match {
                    type enumeration {
                        enum flowspec_community_route-filter-v6_exact-match;
                    }
                }                  //flowspec_community_route-filter-v6_exact-match
                leaf flowspec_community_route-filter-v6_exact-match_wide {
                    type enumeration {
                        enum flowspec_community_route-filter-v6_exact-match_wide;
                    }
                }                  //wide
                leaf flowspec_community_route-filter-v6_json {
                    type enumeration {
                        enum flowspec_community_route-filter-v6_json;
                    }
                }                  //flowspec_community_route-filter-v6_json
                leaf flowspec_community_route-filter-v6_json_detail {
                    type enumeration {
                        enum flowspec_community_route-filter-v6_json_detail;
                    }
                }                  //detail
                leaf flowspec_community_route-filter-v4_exact-match {
                    type enumeration {
                        enum flowspec_community_route-filter-v4_exact-match;
                    }
                }                  //flowspec_community_route-filter-v4_exact-match
                leaf flowspec_community_route-filter-v4_exact-match_wide {
                    type enumeration {
                        enum flowspec_community_route-filter-v4_exact-match_wide;
                    }
                }                  //wide
                leaf flowspec_community_route-filter-v4_json {
                    type enumeration {
                        enum flowspec_community_route-filter-v4_json;
                    }
                }                  //flowspec_community_route-filter-v4_json
                leaf flowspec_community_route-filter-v4_json_detail {
                    type enumeration {
                        enum flowspec_community_route-filter-v4_json_detail;
                    }
                }                  //detail
                leaf flowspec_community_route-filter-translated-v6_exact-match {
                    type enumeration {
                        enum flowspec_community_route-filter-translated-v6_exact-match;
                    }
                }                  //flowspec_community_route-filter-translated-v6_exact-match
                leaf flowspec_community_route-filter-translated-v6_exact-match_wide {
                    type enumeration {
                        enum flowspec_community_route-filter-translated-v6_exact-match_wide;
                    }
                }                  //wide
                leaf flowspec_community_route-filter-translated-v6_json {
                    type enumeration {
                        enum flowspec_community_route-filter-translated-v6_json;
                    }
                }                  //flowspec_community_route-filter-translated-v6_json
                leaf flowspec_community_route-filter-translated-v6_json_detail {
                    type enumeration {
                        enum flowspec_community_route-filter-translated-v6_json_detail;
                    }
                }                  //detail
                leaf flowspec_community_route-filter-translated-v4_exact-match {
                    type enumeration {
                        enum flowspec_community_route-filter-translated-v4_exact-match;
                    }
                }                  //flowspec_community_route-filter-translated-v4_exact-match
                leaf flowspec_community_route-filter-translated-v4_exact-match_wide {
                    type enumeration {
                        enum flowspec_community_route-filter-translated-v4_exact-match_wide;
                    }
                }                  //wide
                leaf flowspec_community_route-filter-translated-v4_json {
                    type enumeration {
                        enum flowspec_community_route-filter-translated-v4_json;
                    }
                }                  //flowspec_community_route-filter-translated-v4_json
                leaf flowspec_community_route-filter-translated-v4_json_detail {
                    type enumeration {
                        enum flowspec_community_route-filter-translated-v4_json_detail;
                    }
                }                  //detail
                leaf flowspec_community_exact-match_json {
                    type enumeration {
                        enum flowspec_community_exact-match_json;
                    }
                }                  //flowspec_community_exact-match_json
                leaf flowspec_community_exact-match_json_detail {
                    type enumeration {
                        enum flowspec_community_exact-match_json_detail;
                    }
                }                  //detail
                leaf flowspec_summary_established_terse {
                    type enumeration {
                        enum flowspec_summary_established_terse;
                    }
                }                  //flowspec_summary_established_terse
                leaf flowspec_summary_established_terse_json {
                    type enumeration {
                        enum flowspec_summary_established_terse_json;
                    }
                }                  //json
                leaf flowspec_summary_established_wide {
                    type enumeration {
                        enum flowspec_summary_established_wide;
                    }
                }                  //flowspec_summary_established_wide
                leaf flowspec_summary_established_wide_json {
                    type enumeration {
                        enum flowspec_summary_established_wide_json;
                    }
                }                  //json
                leaf flowspec_summary_failed_terse {
                    type enumeration {
                        enum flowspec_summary_failed_terse;
                    }
                }                  //flowspec_summary_failed_terse
                leaf flowspec_summary_failed_terse_json {
                    type enumeration {
                        enum flowspec_summary_failed_terse_json;
                    }
                }                  //json
                leaf flowspec_summary_failed_wide {
                    type enumeration {
                        enum flowspec_summary_failed_wide;
                    }
                }                  //flowspec_summary_failed_wide
                leaf flowspec_summary_failed_wide_json {
                    type enumeration {
                        enum flowspec_summary_failed_wide_json;
                    }
                }                  //json
                leaf flowspec_summary_terse_wide {
                    type enumeration {
                        enum flowspec_summary_terse_wide;
                    }
                }                  //flowspec_summary_terse_wide
                leaf flowspec_summary_terse_wide_json {
                    type enumeration {
                        enum flowspec_summary_terse_wide_json;
                    }
                }                  //json
                leaf vpn_all_cidr-only_json {
                    type enumeration {
                        enum vpn_all_cidr-only_json;
                    }
                }                  //vpn_all_cidr-only_json
                leaf vpn_all_cidr-only_json_detail {
                    type enumeration {
                        enum vpn_all_cidr-only_json_detail;
                    }
                }                  //detail
                leaf vpn_all_dampening_parameters {
                    type enumeration {
                        enum vpn_all_dampening_parameters;
                    }
                }                  //vpn_all_dampening_parameters
                leaf vpn_all_dampening_parameters_json {
                    type enumeration {
                        enum vpn_all_dampening_parameters_json;
                    }
                }                  //json
                leaf vpn_all_community_local-AS {
                    type enumeration {
                        enum vpn_all_community_local-AS;
                    }
                }                  //vpn_all_community_local-AS
                leaf vpn_all_community_local-AS_wide {
                    type enumeration {
                        enum vpn_all_community_local-AS_wide;
                    }
                }                  //wide
                leaf vpn_all_community_no-advertise {
                    type enumeration {
                        enum vpn_all_community_no-advertise;
                    }
                }                  //vpn_all_community_no-advertise
                leaf vpn_all_community_no-advertise_wide {
                    type enumeration {
                        enum vpn_all_community_no-advertise_wide;
                    }
                }                  //wide
                leaf vpn_all_community_no-export {
                    type enumeration {
                        enum vpn_all_community_no-export;
                    }
                }                  //vpn_all_community_no-export
                leaf vpn_all_community_no-export_wide {
                    type enumeration {
                        enum vpn_all_community_no-export_wide;
                    }
                }                  //wide
                leaf vpn_all_community_graceful-shutdown {
                    type enumeration {
                        enum vpn_all_community_graceful-shutdown;
                    }
                }                  //vpn_all_community_graceful-shutdown
                leaf vpn_all_community_graceful-shutdown_wide {
                    type enumeration {
                        enum vpn_all_community_graceful-shutdown_wide;
                    }
                }                  //wide
                leaf vpn_all_community_no-peer {
                    type enumeration {
                        enum vpn_all_community_no-peer;
                    }
                }                  //vpn_all_community_no-peer
                leaf vpn_all_community_no-peer_wide {
                    type enumeration {
                        enum vpn_all_community_no-peer_wide;
                    }
                }                  //wide
                leaf vpn_all_community_blackhole {
                    type enumeration {
                        enum vpn_all_community_blackhole;
                    }
                }                  //vpn_all_community_blackhole
                leaf vpn_all_community_blackhole_wide {
                    type enumeration {
                        enum vpn_all_community_blackhole_wide;
                    }
                }                  //wide
                leaf vpn_all_community_llgr-stale {
                    type enumeration {
                        enum vpn_all_community_llgr-stale;
                    }
                }                  //vpn_all_community_llgr-stale
                leaf vpn_all_community_llgr-stale_wide {
                    type enumeration {
                        enum vpn_all_community_llgr-stale_wide;
                    }
                }                  //wide
                leaf vpn_all_community_no-llgr {
                    type enumeration {
                        enum vpn_all_community_no-llgr;
                    }
                }                  //vpn_all_community_no-llgr
                leaf vpn_all_community_no-llgr_wide {
                    type enumeration {
                        enum vpn_all_community_no-llgr_wide;
                    }
                }                  //wide
                leaf vpn_all_community_accept-own {
                    type enumeration {
                        enum vpn_all_community_accept-own;
                    }
                }                  //vpn_all_community_accept-own
                leaf vpn_all_community_accept-own_wide {
                    type enumeration {
                        enum vpn_all_community_accept-own_wide;
                    }
                }                  //wide
                leaf vpn_all_community_accept-own-nexthop {
                    type enumeration {
                        enum vpn_all_community_accept-own-nexthop;
                    }
                }                  //vpn_all_community_accept-own-nexthop
                leaf vpn_all_community_accept-own-nexthop_wide {
                    type enumeration {
                        enum vpn_all_community_accept-own-nexthop_wide;
                    }
                }                  //wide
                leaf vpn_all_community_route-filter-v6 {
                    type enumeration {
                        enum vpn_all_community_route-filter-v6;
                    }
                }                  //vpn_all_community_route-filter-v6
                leaf vpn_all_community_route-filter-v6_wide {
                    type enumeration {
                        enum vpn_all_community_route-filter-v6_wide;
                    }
                }                  //wide
                leaf vpn_all_community_route-filter-v4 {
                    type enumeration {
                        enum vpn_all_community_route-filter-v4;
                    }
                }                  //vpn_all_community_route-filter-v4
                leaf vpn_all_community_route-filter-v4_wide {
                    type enumeration {
                        enum vpn_all_community_route-filter-v4_wide;
                    }
                }                  //wide
                leaf vpn_all_community_route-filter-translated-v6 {
                    type enumeration {
                        enum vpn_all_community_route-filter-translated-v6;
                    }
                }                  //vpn_all_community_route-filter-translated-v6
                leaf vpn_all_community_route-filter-translated-v6_wide {
                    type enumeration {
                        enum vpn_all_community_route-filter-translated-v6_wide;
                    }
                }                  //wide
                leaf vpn_all_community_route-filter-translated-v4 {
                    type enumeration {
                        enum vpn_all_community_route-filter-translated-v4;
                    }
                }                  //vpn_all_community_route-filter-translated-v4
                leaf vpn_all_community_route-filter-translated-v4_wide {
                    type enumeration {
                        enum vpn_all_community_route-filter-translated-v4_wide;
                    }
                }                  //wide
                leaf vpn_all_community_exact-match {
                    type enumeration {
                        enum vpn_all_community_exact-match;
                    }
                }                  //vpn_all_community_exact-match
                leaf vpn_all_community_exact-match_wide {
                    type enumeration {
                        enum vpn_all_community_exact-match_wide;
                    }
                }                  //wide
                leaf vpn_all_community_json {
                    type enumeration {
                        enum vpn_all_community_json;
                    }
                }                  //vpn_all_community_json
                leaf vpn_all_community_json_detail {
                    type enumeration {
                        enum vpn_all_community_json_detail;
                    }
                }                  //detail
                leaf vpn_all_detail-routes_json {
                    type enumeration {
                        enum vpn_all_detail-routes_json;
                    }
                }                  //vpn_all_detail-routes_json
                leaf vpn_all_detail-routes_json_detail {
                    type enumeration {
                        enum vpn_all_detail-routes_json_detail;
                    }
                }                  //detail
                leaf vpn_all_summary_established {
                    type enumeration {
                        enum vpn_all_summary_established;
                    }
                }                  //vpn_all_summary_established
                leaf vpn_all_summary_established_neighbor {
                    type enumeration {
                        enum vpn_all_summary_established_neighbor;
                    }
                }                  //neighbor
                leaf vpn_all_summary_established_remote-as {
                    type enumeration {
                        enum vpn_all_summary_established_remote-as;
                    }
                }                  //remote-as
                leaf vpn_all_summary_established_json {
                    type enumeration {
                        enum vpn_all_summary_established_json;
                    }
                }                  //json
                leaf vpn_all_summary_failed {
                    type enumeration {
                        enum vpn_all_summary_failed;
                    }
                }                  //vpn_all_summary_failed
                leaf vpn_all_summary_failed_neighbor {
                    type enumeration {
                        enum vpn_all_summary_failed_neighbor;
                    }
                }                  //neighbor
                leaf vpn_all_summary_failed_remote-as {
                    type enumeration {
                        enum vpn_all_summary_failed_remote-as;
                    }
                }                  //remote-as
                leaf vpn_all_summary_failed_json {
                    type enumeration {
                        enum vpn_all_summary_failed_json;
                    }
                }                  //json
                leaf vpn_all_summary_terse {
                    type enumeration {
                        enum vpn_all_summary_terse;
                    }
                }                  //vpn_all_summary_terse
                leaf vpn_all_summary_terse_json {
                    type enumeration {
                        enum vpn_all_summary_terse_json;
                    }
                }                  //json
                leaf vpn_all_summary_wide {
                    type enumeration {
                        enum vpn_all_summary_wide;
                    }
                }                  //vpn_all_summary_wide
                leaf vpn_all_summary_wide_json {
                    type enumeration {
                        enum vpn_all_summary_wide_json;
                    }
                }                  //json
                leaf vpn_community_local-AS_exact-match {
                    type enumeration {
                        enum vpn_community_local-AS_exact-match;
                    }
                }                  //vpn_community_local-AS_exact-match
                leaf vpn_community_local-AS_exact-match_wide {
                    type enumeration {
                        enum vpn_community_local-AS_exact-match_wide;
                    }
                }                  //wide
                leaf vpn_community_local-AS_json {
                    type enumeration {
                        enum vpn_community_local-AS_json;
                    }
                }                  //vpn_community_local-AS_json
                leaf vpn_community_local-AS_json_detail {
                    type enumeration {
                        enum vpn_community_local-AS_json_detail;
                    }
                }                  //detail
                leaf vpn_community_no-advertise_exact-match {
                    type enumeration {
                        enum vpn_community_no-advertise_exact-match;
                    }
                }                  //vpn_community_no-advertise_exact-match
                leaf vpn_community_no-advertise_exact-match_wide {
                    type enumeration {
                        enum vpn_community_no-advertise_exact-match_wide;
                    }
                }                  //wide
                leaf vpn_community_no-advertise_json {
                    type enumeration {
                        enum vpn_community_no-advertise_json;
                    }
                }                  //vpn_community_no-advertise_json
                leaf vpn_community_no-advertise_json_detail {
                    type enumeration {
                        enum vpn_community_no-advertise_json_detail;
                    }
                }                  //detail
                leaf vpn_community_no-export_exact-match {
                    type enumeration {
                        enum vpn_community_no-export_exact-match;
                    }
                }                  //vpn_community_no-export_exact-match
                leaf vpn_community_no-export_exact-match_wide {
                    type enumeration {
                        enum vpn_community_no-export_exact-match_wide;
                    }
                }                  //wide
                leaf vpn_community_no-export_json {
                    type enumeration {
                        enum vpn_community_no-export_json;
                    }
                }                  //vpn_community_no-export_json
                leaf vpn_community_no-export_json_detail {
                    type enumeration {
                        enum vpn_community_no-export_json_detail;
                    }
                }                  //detail
                leaf vpn_community_graceful-shutdown_exact-match {
                    type enumeration {
                        enum vpn_community_graceful-shutdown_exact-match;
                    }
                }                  //vpn_community_graceful-shutdown_exact-match
                leaf vpn_community_graceful-shutdown_exact-match_wide {
                    type enumeration {
                        enum vpn_community_graceful-shutdown_exact-match_wide;
                    }
                }                  //wide
                leaf vpn_community_graceful-shutdown_json {
                    type enumeration {
                        enum vpn_community_graceful-shutdown_json;
                    }
                }                  //vpn_community_graceful-shutdown_json
                leaf vpn_community_graceful-shutdown_json_detail {
                    type enumeration {
                        enum vpn_community_graceful-shutdown_json_detail;
                    }
                }                  //detail
                leaf vpn_community_no-peer_exact-match {
                    type enumeration {
                        enum vpn_community_no-peer_exact-match;
                    }
                }                  //vpn_community_no-peer_exact-match
                leaf vpn_community_no-peer_exact-match_wide {
                    type enumeration {
                        enum vpn_community_no-peer_exact-match_wide;
                    }
                }                  //wide
                leaf vpn_community_no-peer_json {
                    type enumeration {
                        enum vpn_community_no-peer_json;
                    }
                }                  //vpn_community_no-peer_json
                leaf vpn_community_no-peer_json_detail {
                    type enumeration {
                        enum vpn_community_no-peer_json_detail;
                    }
                }                  //detail
                leaf vpn_community_blackhole_exact-match {
                    type enumeration {
                        enum vpn_community_blackhole_exact-match;
                    }
                }                  //vpn_community_blackhole_exact-match
                leaf vpn_community_blackhole_exact-match_wide {
                    type enumeration {
                        enum vpn_community_blackhole_exact-match_wide;
                    }
                }                  //wide
                leaf vpn_community_blackhole_json {
                    type enumeration {
                        enum vpn_community_blackhole_json;
                    }
                }                  //vpn_community_blackhole_json
                leaf vpn_community_blackhole_json_detail {
                    type enumeration {
                        enum vpn_community_blackhole_json_detail;
                    }
                }                  //detail
                leaf vpn_community_llgr-stale_exact-match {
                    type enumeration {
                        enum vpn_community_llgr-stale_exact-match;
                    }
                }                  //vpn_community_llgr-stale_exact-match
                leaf vpn_community_llgr-stale_exact-match_wide {
                    type enumeration {
                        enum vpn_community_llgr-stale_exact-match_wide;
                    }
                }                  //wide
                leaf vpn_community_llgr-stale_json {
                    type enumeration {
                        enum vpn_community_llgr-stale_json;
                    }
                }                  //vpn_community_llgr-stale_json
                leaf vpn_community_llgr-stale_json_detail {
                    type enumeration {
                        enum vpn_community_llgr-stale_json_detail;
                    }
                }                  //detail
                leaf vpn_community_no-llgr_exact-match {
                    type enumeration {
                        enum vpn_community_no-llgr_exact-match;
                    }
                }                  //vpn_community_no-llgr_exact-match
                leaf vpn_community_no-llgr_exact-match_wide {
                    type enumeration {
                        enum vpn_community_no-llgr_exact-match_wide;
                    }
                }                  //wide
                leaf vpn_community_no-llgr_json {
                    type enumeration {
                        enum vpn_community_no-llgr_json;
                    }
                }                  //vpn_community_no-llgr_json
                leaf vpn_community_no-llgr_json_detail {
                    type enumeration {
                        enum vpn_community_no-llgr_json_detail;
                    }
                }                  //detail
                leaf vpn_community_accept-own_exact-match {
                    type enumeration {
                        enum vpn_community_accept-own_exact-match;
                    }
                }                  //vpn_community_accept-own_exact-match
                leaf vpn_community_accept-own_exact-match_wide {
                    type enumeration {
                        enum vpn_community_accept-own_exact-match_wide;
                    }
                }                  //wide
                leaf vpn_community_accept-own_json {
                    type enumeration {
                        enum vpn_community_accept-own_json;
                    }
                }                  //vpn_community_accept-own_json
                leaf vpn_community_accept-own_json_detail {
                    type enumeration {
                        enum vpn_community_accept-own_json_detail;
                    }
                }                  //detail
                leaf vpn_community_accept-own-nexthop_exact-match {
                    type enumeration {
                        enum vpn_community_accept-own-nexthop_exact-match;
                    }
                }                  //vpn_community_accept-own-nexthop_exact-match
                leaf vpn_community_accept-own-nexthop_exact-match_wide {
                    type enumeration {
                        enum vpn_community_accept-own-nexthop_exact-match_wide;
                    }
                }                  //wide
                leaf vpn_community_accept-own-nexthop_json {
                    type enumeration {
                        enum vpn_community_accept-own-nexthop_json;
                    }
                }                  //vpn_community_accept-own-nexthop_json
                leaf vpn_community_accept-own-nexthop_json_detail {
                    type enumeration {
                        enum vpn_community_accept-own-nexthop_json_detail;
                    }
                }                  //detail
                leaf vpn_community_route-filter-v6_exact-match {
                    type enumeration {
                        enum vpn_community_route-filter-v6_exact-match;
                    }
                }                  //vpn_community_route-filter-v6_exact-match
                leaf vpn_community_route-filter-v6_exact-match_wide {
                    type enumeration {
                        enum vpn_community_route-filter-v6_exact-match_wide;
                    }
                }                  //wide
                leaf vpn_community_route-filter-v6_json {
                    type enumeration {
                        enum vpn_community_route-filter-v6_json;
                    }
                }                  //vpn_community_route-filter-v6_json
                leaf vpn_community_route-filter-v6_json_detail {
                    type enumeration {
                        enum vpn_community_route-filter-v6_json_detail;
                    }
                }                  //detail
                leaf vpn_community_route-filter-v4_exact-match {
                    type enumeration {
                        enum vpn_community_route-filter-v4_exact-match;
                    }
                }                  //vpn_community_route-filter-v4_exact-match
                leaf vpn_community_route-filter-v4_exact-match_wide {
                    type enumeration {
                        enum vpn_community_route-filter-v4_exact-match_wide;
                    }
                }                  //wide
                leaf vpn_community_route-filter-v4_json {
                    type enumeration {
                        enum vpn_community_route-filter-v4_json;
                    }
                }                  //vpn_community_route-filter-v4_json
                leaf vpn_community_route-filter-v4_json_detail {
                    type enumeration {
                        enum vpn_community_route-filter-v4_json_detail;
                    }
                }                  //detail
                leaf vpn_community_route-filter-translated-v6_exact-match {
                    type enumeration {
                        enum vpn_community_route-filter-translated-v6_exact-match;
                    }
                }                  //vpn_community_route-filter-translated-v6_exact-match
                leaf vpn_community_route-filter-translated-v6_exact-match_wide {
                    type enumeration {
                        enum vpn_community_route-filter-translated-v6_exact-match_wide;
                    }
                }                  //wide
                leaf vpn_community_route-filter-translated-v6_json {
                    type enumeration {
                        enum vpn_community_route-filter-translated-v6_json;
                    }
                }                  //vpn_community_route-filter-translated-v6_json
                leaf vpn_community_route-filter-translated-v6_json_detail {
                    type enumeration {
                        enum vpn_community_route-filter-translated-v6_json_detail;
                    }
                }                  //detail
                leaf vpn_community_route-filter-translated-v4_exact-match {
                    type enumeration {
                        enum vpn_community_route-filter-translated-v4_exact-match;
                    }
                }                  //vpn_community_route-filter-translated-v4_exact-match
                leaf vpn_community_route-filter-translated-v4_exact-match_wide {
                    type enumeration {
                        enum vpn_community_route-filter-translated-v4_exact-match_wide;
                    }
                }                  //wide
                leaf vpn_community_route-filter-translated-v4_json {
                    type enumeration {
                        enum vpn_community_route-filter-translated-v4_json;
                    }
                }                  //vpn_community_route-filter-translated-v4_json
                leaf vpn_community_route-filter-translated-v4_json_detail {
                    type enumeration {
                        enum vpn_community_route-filter-translated-v4_json_detail;
                    }
                }                  //detail
                leaf vpn_community_exact-match_json {
                    type enumeration {
                        enum vpn_community_exact-match_json;
                    }
                }                  //vpn_community_exact-match_json
                leaf vpn_community_exact-match_json_detail {
                    type enumeration {
                        enum vpn_community_exact-match_json_detail;
                    }
                }                  //detail
                leaf vpn_summary_established_terse {
                    type enumeration {
                        enum vpn_summary_established_terse;
                    }
                }                  //vpn_summary_established_terse
                leaf vpn_summary_established_terse_json {
                    type enumeration {
                        enum vpn_summary_established_terse_json;
                    }
                }                  //json
                leaf vpn_summary_established_wide {
                    type enumeration {
                        enum vpn_summary_established_wide;
                    }
                }                  //vpn_summary_established_wide
                leaf vpn_summary_established_wide_json {
                    type enumeration {
                        enum vpn_summary_established_wide_json;
                    }
                }                  //json
                leaf vpn_summary_failed_terse {
                    type enumeration {
                        enum vpn_summary_failed_terse;
                    }
                }                  //vpn_summary_failed_terse
                leaf vpn_summary_failed_terse_json {
                    type enumeration {
                        enum vpn_summary_failed_terse_json;
                    }
                }                  //json
                leaf vpn_summary_failed_wide {
                    type enumeration {
                        enum vpn_summary_failed_wide;
                    }
                }                  //vpn_summary_failed_wide
                leaf vpn_summary_failed_wide_json {
                    type enumeration {
                        enum vpn_summary_failed_wide_json;
                    }
                }                  //json
                leaf vpn_summary_terse_wide {
                    type enumeration {
                        enum vpn_summary_terse_wide;
                    }
                }                  //vpn_summary_terse_wide
                leaf vpn_summary_terse_wide_json {
                    type enumeration {
                        enum vpn_summary_terse_wide_json;
                    }
                }                  //json
                leaf unicast_all_community_local-AS_exact-match {
                    type enumeration {
                        enum unicast_all_community_local-AS_exact-match;
                    }
                }                  //unicast_all_community_local-AS_exact-match
                leaf unicast_all_community_local-AS_exact-match_wide {
                    type enumeration {
                        enum unicast_all_community_local-AS_exact-match_wide;
                    }
                }                  //wide
                leaf unicast_all_community_local-AS_json {
                    type enumeration {
                        enum unicast_all_community_local-AS_json;
                    }
                }                  //unicast_all_community_local-AS_json
                leaf unicast_all_community_local-AS_json_detail {
                    type enumeration {
                        enum unicast_all_community_local-AS_json_detail;
                    }
                }                  //detail
                leaf unicast_all_community_no-advertise_exact-match {
                    type enumeration {
                        enum unicast_all_community_no-advertise_exact-match;
                    }
                }                  //unicast_all_community_no-advertise_exact-match
                leaf unicast_all_community_no-advertise_exact-match_wide {
                    type enumeration {
                        enum unicast_all_community_no-advertise_exact-match_wide;
                    }
                }                  //wide
                leaf unicast_all_community_no-advertise_json {
                    type enumeration {
                        enum unicast_all_community_no-advertise_json;
                    }
                }                  //unicast_all_community_no-advertise_json
                leaf unicast_all_community_no-advertise_json_detail {
                    type enumeration {
                        enum unicast_all_community_no-advertise_json_detail;
                    }
                }                  //detail
                leaf unicast_all_community_no-export_exact-match {
                    type enumeration {
                        enum unicast_all_community_no-export_exact-match;
                    }
                }                  //unicast_all_community_no-export_exact-match
                leaf unicast_all_community_no-export_exact-match_wide {
                    type enumeration {
                        enum unicast_all_community_no-export_exact-match_wide;
                    }
                }                  //wide
                leaf unicast_all_community_no-export_json {
                    type enumeration {
                        enum unicast_all_community_no-export_json;
                    }
                }                  //unicast_all_community_no-export_json
                leaf unicast_all_community_no-export_json_detail {
                    type enumeration {
                        enum unicast_all_community_no-export_json_detail;
                    }
                }                  //detail
                leaf unicast_all_community_graceful-shutdown_exact-match {
                    type enumeration {
                        enum unicast_all_community_graceful-shutdown_exact-match;
                    }
                }                  //unicast_all_community_graceful-shutdown_exact-match
                leaf unicast_all_community_graceful-shutdown_exact-match_wide {
                    type enumeration {
                        enum unicast_all_community_graceful-shutdown_exact-match_wide;
                    }
                }                  //wide
                leaf unicast_all_community_graceful-shutdown_json {
                    type enumeration {
                        enum unicast_all_community_graceful-shutdown_json;
                    }
                }                  //unicast_all_community_graceful-shutdown_json
                leaf unicast_all_community_graceful-shutdown_json_detail {
                    type enumeration {
                        enum unicast_all_community_graceful-shutdown_json_detail;
                    }
                }                  //detail
                leaf unicast_all_community_no-peer_exact-match {
                    type enumeration {
                        enum unicast_all_community_no-peer_exact-match;
                    }
                }                  //unicast_all_community_no-peer_exact-match
                leaf unicast_all_community_no-peer_exact-match_wide {
                    type enumeration {
                        enum unicast_all_community_no-peer_exact-match_wide;
                    }
                }                  //wide
                leaf unicast_all_community_no-peer_json {
                    type enumeration {
                        enum unicast_all_community_no-peer_json;
                    }
                }                  //unicast_all_community_no-peer_json
                leaf unicast_all_community_no-peer_json_detail {
                    type enumeration {
                        enum unicast_all_community_no-peer_json_detail;
                    }
                }                  //detail
                leaf unicast_all_community_blackhole_exact-match {
                    type enumeration {
                        enum unicast_all_community_blackhole_exact-match;
                    }
                }                  //unicast_all_community_blackhole_exact-match
                leaf unicast_all_community_blackhole_exact-match_wide {
                    type enumeration {
                        enum unicast_all_community_blackhole_exact-match_wide;
                    }
                }                  //wide
                leaf unicast_all_community_blackhole_json {
                    type enumeration {
                        enum unicast_all_community_blackhole_json;
                    }
                }                  //unicast_all_community_blackhole_json
                leaf unicast_all_community_blackhole_json_detail {
                    type enumeration {
                        enum unicast_all_community_blackhole_json_detail;
                    }
                }                  //detail
                leaf unicast_all_community_llgr-stale_exact-match {
                    type enumeration {
                        enum unicast_all_community_llgr-stale_exact-match;
                    }
                }                  //unicast_all_community_llgr-stale_exact-match
                leaf unicast_all_community_llgr-stale_exact-match_wide {
                    type enumeration {
                        enum unicast_all_community_llgr-stale_exact-match_wide;
                    }
                }                  //wide
                leaf unicast_all_community_llgr-stale_json {
                    type enumeration {
                        enum unicast_all_community_llgr-stale_json;
                    }
                }                  //unicast_all_community_llgr-stale_json
                leaf unicast_all_community_llgr-stale_json_detail {
                    type enumeration {
                        enum unicast_all_community_llgr-stale_json_detail;
                    }
                }                  //detail
                leaf unicast_all_community_no-llgr_exact-match {
                    type enumeration {
                        enum unicast_all_community_no-llgr_exact-match;
                    }
                }                  //unicast_all_community_no-llgr_exact-match
                leaf unicast_all_community_no-llgr_exact-match_wide {
                    type enumeration {
                        enum unicast_all_community_no-llgr_exact-match_wide;
                    }
                }                  //wide
                leaf unicast_all_community_no-llgr_json {
                    type enumeration {
                        enum unicast_all_community_no-llgr_json;
                    }
                }                  //unicast_all_community_no-llgr_json
                leaf unicast_all_community_no-llgr_json_detail {
                    type enumeration {
                        enum unicast_all_community_no-llgr_json_detail;
                    }
                }                  //detail
                leaf unicast_all_community_accept-own_exact-match {
                    type enumeration {
                        enum unicast_all_community_accept-own_exact-match;
                    }
                }                  //unicast_all_community_accept-own_exact-match
                leaf unicast_all_community_accept-own_exact-match_wide {
                    type enumeration {
                        enum unicast_all_community_accept-own_exact-match_wide;
                    }
                }                  //wide
                leaf unicast_all_community_accept-own_json {
                    type enumeration {
                        enum unicast_all_community_accept-own_json;
                    }
                }                  //unicast_all_community_accept-own_json
                leaf unicast_all_community_accept-own_json_detail {
                    type enumeration {
                        enum unicast_all_community_accept-own_json_detail;
                    }
                }                  //detail
                leaf unicast_all_community_accept-own-nexthop_exact-match {
                    type enumeration {
                        enum unicast_all_community_accept-own-nexthop_exact-match;
                    }
                }                  //unicast_all_community_accept-own-nexthop_exact-match
                leaf unicast_all_community_accept-own-nexthop_exact-match_wide {
                    type enumeration {
                        enum unicast_all_community_accept-own-nexthop_exact-match_wide;
                    }
                }                  //wide
                leaf unicast_all_community_accept-own-nexthop_json {
                    type enumeration {
                        enum unicast_all_community_accept-own-nexthop_json;
                    }
                }                  //unicast_all_community_accept-own-nexthop_json
                leaf unicast_all_community_accept-own-nexthop_json_detail {
                    type enumeration {
                        enum unicast_all_community_accept-own-nexthop_json_detail;
                    }
                }                  //detail
                leaf unicast_all_community_route-filter-v6_exact-match {
                    type enumeration {
                        enum unicast_all_community_route-filter-v6_exact-match;
                    }
                }                  //unicast_all_community_route-filter-v6_exact-match
                leaf unicast_all_community_route-filter-v6_exact-match_wide {
                    type enumeration {
                        enum unicast_all_community_route-filter-v6_exact-match_wide;
                    }
                }                  //wide
                leaf unicast_all_community_route-filter-v6_json {
                    type enumeration {
                        enum unicast_all_community_route-filter-v6_json;
                    }
                }                  //unicast_all_community_route-filter-v6_json
                leaf unicast_all_community_route-filter-v6_json_detail {
                    type enumeration {
                        enum unicast_all_community_route-filter-v6_json_detail;
                    }
                }                  //detail
                leaf unicast_all_community_route-filter-v4_exact-match {
                    type enumeration {
                        enum unicast_all_community_route-filter-v4_exact-match;
                    }
                }                  //unicast_all_community_route-filter-v4_exact-match
                leaf unicast_all_community_route-filter-v4_exact-match_wide {
                    type enumeration {
                        enum unicast_all_community_route-filter-v4_exact-match_wide;
                    }
                }                  //wide
                leaf unicast_all_community_route-filter-v4_json {
                    type enumeration {
                        enum unicast_all_community_route-filter-v4_json;
                    }
                }                  //unicast_all_community_route-filter-v4_json
                leaf unicast_all_community_route-filter-v4_json_detail {
                    type enumeration {
                        enum unicast_all_community_route-filter-v4_json_detail;
                    }
                }                  //detail
                leaf unicast_all_community_route-filter-translated-v6_exact-match {
                    type enumeration {
                        enum unicast_all_community_route-filter-translated-v6_exact-match;
                    }
                }                  //unicast_all_community_route-filter-translated-v6_exact-match
                leaf unicast_all_community_route-filter-translated-v6_exact-match_wide {
                    type enumeration {
                        enum unicast_all_community_route-filter-translated-v6_exact-match_wide;
                    }
                }                  //wide
                leaf unicast_all_community_route-filter-translated-v6_json {
                    type enumeration {
                        enum unicast_all_community_route-filter-translated-v6_json;
                    }
                }                  //unicast_all_community_route-filter-translated-v6_json
                leaf unicast_all_community_route-filter-translated-v6_json_detail {
                    type enumeration {
                        enum unicast_all_community_route-filter-translated-v6_json_detail;
                    }
                }                  //detail
                leaf unicast_all_community_route-filter-translated-v4_exact-match {
                    type enumeration {
                        enum unicast_all_community_route-filter-translated-v4_exact-match;
                    }
                }                  //unicast_all_community_route-filter-translated-v4_exact-match
                leaf unicast_all_community_route-filter-translated-v4_exact-match_wide {
                    type enumeration {
                        enum unicast_all_community_route-filter-translated-v4_exact-match_wide;
                    }
                }                  //wide
                leaf unicast_all_community_route-filter-translated-v4_json {
                    type enumeration {
                        enum unicast_all_community_route-filter-translated-v4_json;
                    }
                }                  //unicast_all_community_route-filter-translated-v4_json
                leaf unicast_all_community_route-filter-translated-v4_json_detail {
                    type enumeration {
                        enum unicast_all_community_route-filter-translated-v4_json_detail;
                    }
                }                  //detail
                leaf unicast_all_community_exact-match_json {
                    type enumeration {
                        enum unicast_all_community_exact-match_json;
                    }
                }                  //unicast_all_community_exact-match_json
                leaf unicast_all_community_exact-match_json_detail {
                    type enumeration {
                        enum unicast_all_community_exact-match_json_detail;
                    }
                }                  //detail
                leaf unicast_all_summary_established_terse {
                    type enumeration {
                        enum unicast_all_summary_established_terse;
                    }
                }                  //unicast_all_summary_established_terse
                leaf unicast_all_summary_established_terse_json {
                    type enumeration {
                        enum unicast_all_summary_established_terse_json;
                    }
                }                  //json
                leaf unicast_all_summary_established_wide {
                    type enumeration {
                        enum unicast_all_summary_established_wide;
                    }
                }                  //unicast_all_summary_established_wide
                leaf unicast_all_summary_established_wide_json {
                    type enumeration {
                        enum unicast_all_summary_established_wide_json;
                    }
                }                  //json
                leaf unicast_all_summary_failed_terse {
                    type enumeration {
                        enum unicast_all_summary_failed_terse;
                    }
                }                  //unicast_all_summary_failed_terse
                leaf unicast_all_summary_failed_terse_json {
                    type enumeration {
                        enum unicast_all_summary_failed_terse_json;
                    }
                }                  //json
                leaf unicast_all_summary_failed_wide {
                    type enumeration {
                        enum unicast_all_summary_failed_wide;
                    }
                }                  //unicast_all_summary_failed_wide
                leaf unicast_all_summary_failed_wide_json {
                    type enumeration {
                        enum unicast_all_summary_failed_wide_json;
                    }
                }                  //json
                leaf unicast_all_summary_terse_wide {
                    type enumeration {
                        enum unicast_all_summary_terse_wide;
                    }
                }                  //unicast_all_summary_terse_wide
                leaf unicast_all_summary_terse_wide_json {
                    type enumeration {
                        enum unicast_all_summary_terse_wide_json;
                    }
                }                  //json
                leaf unicast_community_local-AS_exact-match_json {
                    type enumeration {
                        enum unicast_community_local-AS_exact-match_json;
                    }
                }                  //unicast_community_local-AS_exact-match_json
                leaf unicast_community_local-AS_exact-match_json_detail {
                    type enumeration {
                        enum unicast_community_local-AS_exact-match_json_detail;
                    }
                }                  //detail
                leaf unicast_community_no-advertise_exact-match_json {
                    type enumeration {
                        enum unicast_community_no-advertise_exact-match_json;
                    }
                }                  //unicast_community_no-advertise_exact-match_json
                leaf unicast_community_no-advertise_exact-match_json_detail {
                    type enumeration {
                        enum unicast_community_no-advertise_exact-match_json_detail;
                    }
                }                  //detail
                leaf unicast_community_no-export_exact-match_json {
                    type enumeration {
                        enum unicast_community_no-export_exact-match_json;
                    }
                }                  //unicast_community_no-export_exact-match_json
                leaf unicast_community_no-export_exact-match_json_detail {
                    type enumeration {
                        enum unicast_community_no-export_exact-match_json_detail;
                    }
                }                  //detail
                leaf unicast_community_graceful-shutdown_exact-match_json {
                    type enumeration {
                        enum unicast_community_graceful-shutdown_exact-match_json;
                    }
                }                  //unicast_community_graceful-shutdown_exact-match_json
                leaf unicast_community_graceful-shutdown_exact-match_json_detail {
                    type enumeration {
                        enum unicast_community_graceful-shutdown_exact-match_json_detail;
                    }
                }                  //detail
                leaf unicast_community_no-peer_exact-match_json {
                    type enumeration {
                        enum unicast_community_no-peer_exact-match_json;
                    }
                }                  //unicast_community_no-peer_exact-match_json
                leaf unicast_community_no-peer_exact-match_json_detail {
                    type enumeration {
                        enum unicast_community_no-peer_exact-match_json_detail;
                    }
                }                  //detail
                leaf unicast_community_blackhole_exact-match_json {
                    type enumeration {
                        enum unicast_community_blackhole_exact-match_json;
                    }
                }                  //unicast_community_blackhole_exact-match_json
                leaf unicast_community_blackhole_exact-match_json_detail {
                    type enumeration {
                        enum unicast_community_blackhole_exact-match_json_detail;
                    }
                }                  //detail
                leaf unicast_community_llgr-stale_exact-match_json {
                    type enumeration {
                        enum unicast_community_llgr-stale_exact-match_json;
                    }
                }                  //unicast_community_llgr-stale_exact-match_json
                leaf unicast_community_llgr-stale_exact-match_json_detail {
                    type enumeration {
                        enum unicast_community_llgr-stale_exact-match_json_detail;
                    }
                }                  //detail
                leaf unicast_community_no-llgr_exact-match_json {
                    type enumeration {
                        enum unicast_community_no-llgr_exact-match_json;
                    }
                }                  //unicast_community_no-llgr_exact-match_json
                leaf unicast_community_no-llgr_exact-match_json_detail {
                    type enumeration {
                        enum unicast_community_no-llgr_exact-match_json_detail;
                    }
                }                  //detail
                leaf unicast_community_accept-own_exact-match_json {
                    type enumeration {
                        enum unicast_community_accept-own_exact-match_json;
                    }
                }                  //unicast_community_accept-own_exact-match_json
                leaf unicast_community_accept-own_exact-match_json_detail {
                    type enumeration {
                        enum unicast_community_accept-own_exact-match_json_detail;
                    }
                }                  //detail
                leaf unicast_community_accept-own-nexthop_exact-match_json {
                    type enumeration {
                        enum unicast_community_accept-own-nexthop_exact-match_json;
                    }
                }                  //unicast_community_accept-own-nexthop_exact-match_json
                leaf unicast_community_accept-own-nexthop_exact-match_json_detail {
                    type enumeration {
                        enum unicast_community_accept-own-nexthop_exact-match_json_detail;
                    }
                }                  //detail
                leaf unicast_community_route-filter-v6_exact-match_json {
                    type enumeration {
                        enum unicast_community_route-filter-v6_exact-match_json;
                    }
                }                  //unicast_community_route-filter-v6_exact-match_json
                leaf unicast_community_route-filter-v6_exact-match_json_detail {
                    type enumeration {
                        enum unicast_community_route-filter-v6_exact-match_json_detail;
                    }
                }                  //detail
                leaf unicast_community_route-filter-v4_exact-match_json {
                    type enumeration {
                        enum unicast_community_route-filter-v4_exact-match_json;
                    }
                }                  //unicast_community_route-filter-v4_exact-match_json
                leaf unicast_community_route-filter-v4_exact-match_json_detail {
                    type enumeration {
                        enum unicast_community_route-filter-v4_exact-match_json_detail;
                    }
                }                  //detail
                leaf unicast_community_route-filter-translated-v6_exact-match_json {
                    type enumeration {
                        enum unicast_community_route-filter-translated-v6_exact-match_json;
                    }
                }                  //unicast_community_route-filter-translated-v6_exact-match_json
                leaf unicast_community_route-filter-translated-v6_exact-match_json_detail {
                    type enumeration {
                        enum unicast_community_route-filter-translated-v6_exact-match_json_detail;
                    }
                }                  //detail
                leaf unicast_community_route-filter-translated-v4_exact-match_json {
                    type enumeration {
                        enum unicast_community_route-filter-translated-v4_exact-match_json;
                    }
                }                  //unicast_community_route-filter-translated-v4_exact-match_json
                leaf unicast_community_route-filter-translated-v4_exact-match_json_detail {
                    type enumeration {
                        enum unicast_community_route-filter-translated-v4_exact-match_json_detail;
                    }
                }                  //detail
                leaf unicast_summary_established_terse_wide {
                    type enumeration {
                        enum unicast_summary_established_terse_wide;
                    }
                }                  //unicast_summary_established_terse_wide
                leaf unicast_summary_established_terse_wide_json {
                    type enumeration {
                        enum unicast_summary_established_terse_wide_json;
                    }
                }                  //json
                leaf unicast_summary_failed_terse_wide {
                    type enumeration {
                        enum unicast_summary_failed_terse_wide;
                    }
                }                  //unicast_summary_failed_terse_wide
                leaf unicast_summary_failed_terse_wide_json {
                    type enumeration {
                        enum unicast_summary_failed_terse_wide_json;
                    }
                }                  //json
                leaf flowspec_all_community_local-AS_exact-match {
                    type enumeration {
                        enum flowspec_all_community_local-AS_exact-match;
                    }
                }                  //flowspec_all_community_local-AS_exact-match
                leaf flowspec_all_community_local-AS_exact-match_wide {
                    type enumeration {
                        enum flowspec_all_community_local-AS_exact-match_wide;
                    }
                }                  //wide
                leaf flowspec_all_community_local-AS_json {
                    type enumeration {
                        enum flowspec_all_community_local-AS_json;
                    }
                }                  //flowspec_all_community_local-AS_json
                leaf flowspec_all_community_local-AS_json_detail {
                    type enumeration {
                        enum flowspec_all_community_local-AS_json_detail;
                    }
                }                  //detail
                leaf flowspec_all_community_no-advertise_exact-match {
                    type enumeration {
                        enum flowspec_all_community_no-advertise_exact-match;
                    }
                }                  //flowspec_all_community_no-advertise_exact-match
                leaf flowspec_all_community_no-advertise_exact-match_wide {
                    type enumeration {
                        enum flowspec_all_community_no-advertise_exact-match_wide;
                    }
                }                  //wide
                leaf flowspec_all_community_no-advertise_json {
                    type enumeration {
                        enum flowspec_all_community_no-advertise_json;
                    }
                }                  //flowspec_all_community_no-advertise_json
                leaf flowspec_all_community_no-advertise_json_detail {
                    type enumeration {
                        enum flowspec_all_community_no-advertise_json_detail;
                    }
                }                  //detail
                leaf flowspec_all_community_no-export_exact-match {
                    type enumeration {
                        enum flowspec_all_community_no-export_exact-match;
                    }
                }                  //flowspec_all_community_no-export_exact-match
                leaf flowspec_all_community_no-export_exact-match_wide {
                    type enumeration {
                        enum flowspec_all_community_no-export_exact-match_wide;
                    }
                }                  //wide
                leaf flowspec_all_community_no-export_json {
                    type enumeration {
                        enum flowspec_all_community_no-export_json;
                    }
                }                  //flowspec_all_community_no-export_json
                leaf flowspec_all_community_no-export_json_detail {
                    type enumeration {
                        enum flowspec_all_community_no-export_json_detail;
                    }
                }                  //detail
                leaf flowspec_all_community_graceful-shutdown_exact-match {
                    type enumeration {
                        enum flowspec_all_community_graceful-shutdown_exact-match;
                    }
                }                  //flowspec_all_community_graceful-shutdown_exact-match
                leaf flowspec_all_community_graceful-shutdown_exact-match_wide {
                    type enumeration {
                        enum flowspec_all_community_graceful-shutdown_exact-match_wide;
                    }
                }                  //wide
                leaf flowspec_all_community_graceful-shutdown_json {
                    type enumeration {
                        enum flowspec_all_community_graceful-shutdown_json;
                    }
                }                  //flowspec_all_community_graceful-shutdown_json
                leaf flowspec_all_community_graceful-shutdown_json_detail {
                    type enumeration {
                        enum flowspec_all_community_graceful-shutdown_json_detail;
                    }
                }                  //detail
                leaf flowspec_all_community_no-peer_exact-match {
                    type enumeration {
                        enum flowspec_all_community_no-peer_exact-match;
                    }
                }                  //flowspec_all_community_no-peer_exact-match
                leaf flowspec_all_community_no-peer_exact-match_wide {
                    type enumeration {
                        enum flowspec_all_community_no-peer_exact-match_wide;
                    }
                }                  //wide
                leaf flowspec_all_community_no-peer_json {
                    type enumeration {
                        enum flowspec_all_community_no-peer_json;
                    }
                }                  //flowspec_all_community_no-peer_json
                leaf flowspec_all_community_no-peer_json_detail {
                    type enumeration {
                        enum flowspec_all_community_no-peer_json_detail;
                    }
                }                  //detail
                leaf flowspec_all_community_blackhole_exact-match {
                    type enumeration {
                        enum flowspec_all_community_blackhole_exact-match;
                    }
                }                  //flowspec_all_community_blackhole_exact-match
                leaf flowspec_all_community_blackhole_exact-match_wide {
                    type enumeration {
                        enum flowspec_all_community_blackhole_exact-match_wide;
                    }
                }                  //wide
                leaf flowspec_all_community_blackhole_json {
                    type enumeration {
                        enum flowspec_all_community_blackhole_json;
                    }
                }                  //flowspec_all_community_blackhole_json
                leaf flowspec_all_community_blackhole_json_detail {
                    type enumeration {
                        enum flowspec_all_community_blackhole_json_detail;
                    }
                }                  //detail
                leaf flowspec_all_community_llgr-stale_exact-match {
                    type enumeration {
                        enum flowspec_all_community_llgr-stale_exact-match;
                    }
                }                  //flowspec_all_community_llgr-stale_exact-match
                leaf flowspec_all_community_llgr-stale_exact-match_wide {
                    type enumeration {
                        enum flowspec_all_community_llgr-stale_exact-match_wide;
                    }
                }                  //wide
                leaf flowspec_all_community_llgr-stale_json {
                    type enumeration {
                        enum flowspec_all_community_llgr-stale_json;
                    }
                }                  //flowspec_all_community_llgr-stale_json
                leaf flowspec_all_community_llgr-stale_json_detail {
                    type enumeration {
                        enum flowspec_all_community_llgr-stale_json_detail;
                    }
                }                  //detail
                leaf flowspec_all_community_no-llgr_exact-match {
                    type enumeration {
                        enum flowspec_all_community_no-llgr_exact-match;
                    }
                }                  //flowspec_all_community_no-llgr_exact-match
                leaf flowspec_all_community_no-llgr_exact-match_wide {
                    type enumeration {
                        enum flowspec_all_community_no-llgr_exact-match_wide;
                    }
                }                  //wide
                leaf flowspec_all_community_no-llgr_json {
                    type enumeration {
                        enum flowspec_all_community_no-llgr_json;
                    }
                }                  //flowspec_all_community_no-llgr_json
                leaf flowspec_all_community_no-llgr_json_detail {
                    type enumeration {
                        enum flowspec_all_community_no-llgr_json_detail;
                    }
                }                  //detail
                leaf flowspec_all_community_accept-own_exact-match {
                    type enumeration {
                        enum flowspec_all_community_accept-own_exact-match;
                    }
                }                  //flowspec_all_community_accept-own_exact-match
                leaf flowspec_all_community_accept-own_exact-match_wide {
                    type enumeration {
                        enum flowspec_all_community_accept-own_exact-match_wide;
                    }
                }                  //wide
                leaf flowspec_all_community_accept-own_json {
                    type enumeration {
                        enum flowspec_all_community_accept-own_json;
                    }
                }                  //flowspec_all_community_accept-own_json
                leaf flowspec_all_community_accept-own_json_detail {
                    type enumeration {
                        enum flowspec_all_community_accept-own_json_detail;
                    }
                }                  //detail
                leaf flowspec_all_community_accept-own-nexthop_exact-match {
                    type enumeration {
                        enum flowspec_all_community_accept-own-nexthop_exact-match;
                    }
                }                  //flowspec_all_community_accept-own-nexthop_exact-match
                leaf flowspec_all_community_accept-own-nexthop_exact-match_wide {
                    type enumeration {
                        enum flowspec_all_community_accept-own-nexthop_exact-match_wide;
                    }
                }                  //wide
                leaf flowspec_all_community_accept-own-nexthop_json {
                    type enumeration {
                        enum flowspec_all_community_accept-own-nexthop_json;
                    }
                }                  //flowspec_all_community_accept-own-nexthop_json
                leaf flowspec_all_community_accept-own-nexthop_json_detail {
                    type enumeration {
                        enum flowspec_all_community_accept-own-nexthop_json_detail;
                    }
                }                  //detail
                leaf flowspec_all_community_route-filter-v6_exact-match {
                    type enumeration {
                        enum flowspec_all_community_route-filter-v6_exact-match;
                    }
                }                  //flowspec_all_community_route-filter-v6_exact-match
                leaf flowspec_all_community_route-filter-v6_exact-match_wide {
                    type enumeration {
                        enum flowspec_all_community_route-filter-v6_exact-match_wide;
                    }
                }                  //wide
                leaf flowspec_all_community_route-filter-v6_json {
                    type enumeration {
                        enum flowspec_all_community_route-filter-v6_json;
                    }
                }                  //flowspec_all_community_route-filter-v6_json
                leaf flowspec_all_community_route-filter-v6_json_detail {
                    type enumeration {
                        enum flowspec_all_community_route-filter-v6_json_detail;
                    }
                }                  //detail
                leaf flowspec_all_community_route-filter-v4_exact-match {
                    type enumeration {
                        enum flowspec_all_community_route-filter-v4_exact-match;
                    }
                }                  //flowspec_all_community_route-filter-v4_exact-match
                leaf flowspec_all_community_route-filter-v4_exact-match_wide {
                    type enumeration {
                        enum flowspec_all_community_route-filter-v4_exact-match_wide;
                    }
                }                  //wide
                leaf flowspec_all_community_route-filter-v4_json {
                    type enumeration {
                        enum flowspec_all_community_route-filter-v4_json;
                    }
                }                  //flowspec_all_community_route-filter-v4_json
                leaf flowspec_all_community_route-filter-v4_json_detail {
                    type enumeration {
                        enum flowspec_all_community_route-filter-v4_json_detail;
                    }
                }                  //detail
                leaf flowspec_all_community_route-filter-translated-v6_exact-match {
                    type enumeration {
                        enum flowspec_all_community_route-filter-translated-v6_exact-match;
                    }
                }                  //flowspec_all_community_route-filter-translated-v6_exact-match
                leaf flowspec_all_community_route-filter-translated-v6_exact-match_wide {
                    type enumeration {
                        enum flowspec_all_community_route-filter-translated-v6_exact-match_wide;
                    }
                }                  //wide
                leaf flowspec_all_community_route-filter-translated-v6_json {
                    type enumeration {
                        enum flowspec_all_community_route-filter-translated-v6_json;
                    }
                }                  //flowspec_all_community_route-filter-translated-v6_json
                leaf flowspec_all_community_route-filter-translated-v6_json_detail {
                    type enumeration {
                        enum flowspec_all_community_route-filter-translated-v6_json_detail;
                    }
                }                  //detail
                leaf flowspec_all_community_route-filter-translated-v4_exact-match {
                    type enumeration {
                        enum flowspec_all_community_route-filter-translated-v4_exact-match;
                    }
                }                  //flowspec_all_community_route-filter-translated-v4_exact-match
                leaf flowspec_all_community_route-filter-translated-v4_exact-match_wide {
                    type enumeration {
                        enum flowspec_all_community_route-filter-translated-v4_exact-match_wide;
                    }
                }                  //wide
                leaf flowspec_all_community_route-filter-translated-v4_json {
                    type enumeration {
                        enum flowspec_all_community_route-filter-translated-v4_json;
                    }
                }                  //flowspec_all_community_route-filter-translated-v4_json
                leaf flowspec_all_community_route-filter-translated-v4_json_detail {
                    type enumeration {
                        enum flowspec_all_community_route-filter-translated-v4_json_detail;
                    }
                }                  //detail
                leaf flowspec_all_community_exact-match_json {
                    type enumeration {
                        enum flowspec_all_community_exact-match_json;
                    }
                }                  //flowspec_all_community_exact-match_json
                leaf flowspec_all_community_exact-match_json_detail {
                    type enumeration {
                        enum flowspec_all_community_exact-match_json_detail;
                    }
                }                  //detail
                leaf flowspec_all_summary_established_terse {
                    type enumeration {
                        enum flowspec_all_summary_established_terse;
                    }
                }                  //flowspec_all_summary_established_terse
                leaf flowspec_all_summary_established_terse_json {
                    type enumeration {
                        enum flowspec_all_summary_established_terse_json;
                    }
                }                  //json
                leaf flowspec_all_summary_established_wide {
                    type enumeration {
                        enum flowspec_all_summary_established_wide;
                    }
                }                  //flowspec_all_summary_established_wide
                leaf flowspec_all_summary_established_wide_json {
                    type enumeration {
                        enum flowspec_all_summary_established_wide_json;
                    }
                }                  //json
                leaf flowspec_all_summary_failed_terse {
                    type enumeration {
                        enum flowspec_all_summary_failed_terse;
                    }
                }                  //flowspec_all_summary_failed_terse
                leaf flowspec_all_summary_failed_terse_json {
                    type enumeration {
                        enum flowspec_all_summary_failed_terse_json;
                    }
                }                  //json
                leaf flowspec_all_summary_failed_wide {
                    type enumeration {
                        enum flowspec_all_summary_failed_wide;
                    }
                }                  //flowspec_all_summary_failed_wide
                leaf flowspec_all_summary_failed_wide_json {
                    type enumeration {
                        enum flowspec_all_summary_failed_wide_json;
                    }
                }                  //json
                leaf flowspec_all_summary_terse_wide {
                    type enumeration {
                        enum flowspec_all_summary_terse_wide;
                    }
                }                  //flowspec_all_summary_terse_wide
                leaf flowspec_all_summary_terse_wide_json {
                    type enumeration {
                        enum flowspec_all_summary_terse_wide_json;
                    }
                }                  //json
                leaf flowspec_community_local-AS_exact-match_json {
                    type enumeration {
                        enum flowspec_community_local-AS_exact-match_json;
                    }
                }                  //flowspec_community_local-AS_exact-match_json
                leaf flowspec_community_local-AS_exact-match_json_detail {
                    type enumeration {
                        enum flowspec_community_local-AS_exact-match_json_detail;
                    }
                }                  //detail
                leaf flowspec_community_no-advertise_exact-match_json {
                    type enumeration {
                        enum flowspec_community_no-advertise_exact-match_json;
                    }
                }                  //flowspec_community_no-advertise_exact-match_json
                leaf flowspec_community_no-advertise_exact-match_json_detail {
                    type enumeration {
                        enum flowspec_community_no-advertise_exact-match_json_detail;
                    }
                }                  //detail
                leaf flowspec_community_no-export_exact-match_json {
                    type enumeration {
                        enum flowspec_community_no-export_exact-match_json;
                    }
                }                  //flowspec_community_no-export_exact-match_json
                leaf flowspec_community_no-export_exact-match_json_detail {
                    type enumeration {
                        enum flowspec_community_no-export_exact-match_json_detail;
                    }
                }                  //detail
                leaf flowspec_community_graceful-shutdown_exact-match_json {
                    type enumeration {
                        enum flowspec_community_graceful-shutdown_exact-match_json;
                    }
                }                  //flowspec_community_graceful-shutdown_exact-match_json
                leaf flowspec_community_graceful-shutdown_exact-match_json_detail {
                    type enumeration {
                        enum flowspec_community_graceful-shutdown_exact-match_json_detail;
                    }
                }                  //detail
                leaf flowspec_community_no-peer_exact-match_json {
                    type enumeration {
                        enum flowspec_community_no-peer_exact-match_json;
                    }
                }                  //flowspec_community_no-peer_exact-match_json
                leaf flowspec_community_no-peer_exact-match_json_detail {
                    type enumeration {
                        enum flowspec_community_no-peer_exact-match_json_detail;
                    }
                }                  //detail
                leaf flowspec_community_blackhole_exact-match_json {
                    type enumeration {
                        enum flowspec_community_blackhole_exact-match_json;
                    }
                }                  //flowspec_community_blackhole_exact-match_json
                leaf flowspec_community_blackhole_exact-match_json_detail {
                    type enumeration {
                        enum flowspec_community_blackhole_exact-match_json_detail;
                    }
                }                  //detail
                leaf flowspec_community_llgr-stale_exact-match_json {
                    type enumeration {
                        enum flowspec_community_llgr-stale_exact-match_json;
                    }
                }                  //flowspec_community_llgr-stale_exact-match_json
                leaf flowspec_community_llgr-stale_exact-match_json_detail {
                    type enumeration {
                        enum flowspec_community_llgr-stale_exact-match_json_detail;
                    }
                }                  //detail
                leaf flowspec_community_no-llgr_exact-match_json {
                    type enumeration {
                        enum flowspec_community_no-llgr_exact-match_json;
                    }
                }                  //flowspec_community_no-llgr_exact-match_json
                leaf flowspec_community_no-llgr_exact-match_json_detail {
                    type enumeration {
                        enum flowspec_community_no-llgr_exact-match_json_detail;
                    }
                }                  //detail
                leaf flowspec_community_accept-own_exact-match_json {
                    type enumeration {
                        enum flowspec_community_accept-own_exact-match_json;
                    }
                }                  //flowspec_community_accept-own_exact-match_json
                leaf flowspec_community_accept-own_exact-match_json_detail {
                    type enumeration {
                        enum flowspec_community_accept-own_exact-match_json_detail;
                    }
                }                  //detail
                leaf flowspec_community_accept-own-nexthop_exact-match_json {
                    type enumeration {
                        enum flowspec_community_accept-own-nexthop_exact-match_json;
                    }
                }                  //flowspec_community_accept-own-nexthop_exact-match_json
                leaf flowspec_community_accept-own-nexthop_exact-match_json_detail {
                    type enumeration {
                        enum flowspec_community_accept-own-nexthop_exact-match_json_detail;
                    }
                }                  //detail
                leaf flowspec_community_route-filter-v6_exact-match_json {
                    type enumeration {
                        enum flowspec_community_route-filter-v6_exact-match_json;
                    }
                }                  //flowspec_community_route-filter-v6_exact-match_json
                leaf flowspec_community_route-filter-v6_exact-match_json_detail {
                    type enumeration {
                        enum flowspec_community_route-filter-v6_exact-match_json_detail;
                    }
                }                  //detail
                leaf flowspec_community_route-filter-v4_exact-match_json {
                    type enumeration {
                        enum flowspec_community_route-filter-v4_exact-match_json;
                    }
                }                  //flowspec_community_route-filter-v4_exact-match_json
                leaf flowspec_community_route-filter-v4_exact-match_json_detail {
                    type enumeration {
                        enum flowspec_community_route-filter-v4_exact-match_json_detail;
                    }
                }                  //detail
                leaf flowspec_community_route-filter-translated-v6_exact-match_json {
                    type enumeration {
                        enum flowspec_community_route-filter-translated-v6_exact-match_json;
                    }
                }                  //flowspec_community_route-filter-translated-v6_exact-match_json
                leaf flowspec_community_route-filter-translated-v6_exact-match_json_detail {
                    type enumeration {
                        enum flowspec_community_route-filter-translated-v6_exact-match_json_detail;
                    }
                }                  //detail
                leaf flowspec_community_route-filter-translated-v4_exact-match_json {
                    type enumeration {
                        enum flowspec_community_route-filter-translated-v4_exact-match_json;
                    }
                }                  //flowspec_community_route-filter-translated-v4_exact-match_json
                leaf flowspec_community_route-filter-translated-v4_exact-match_json_detail {
                    type enumeration {
                        enum flowspec_community_route-filter-translated-v4_exact-match_json_detail;
                    }
                }                  //detail
                leaf flowspec_summary_established_terse_wide {
                    type enumeration {
                        enum flowspec_summary_established_terse_wide;
                    }
                }                  //flowspec_summary_established_terse_wide
                leaf flowspec_summary_established_terse_wide_json {
                    type enumeration {
                        enum flowspec_summary_established_terse_wide_json;
                    }
                }                  //json
                leaf flowspec_summary_failed_terse_wide {
                    type enumeration {
                        enum flowspec_summary_failed_terse_wide;
                    }
                }                  //flowspec_summary_failed_terse_wide
                leaf flowspec_summary_failed_terse_wide_json {
                    type enumeration {
                        enum flowspec_summary_failed_terse_wide_json;
                    }
                }                  //json
                leaf vpn_all_community_local-AS_exact-match {
                    type enumeration {
                        enum vpn_all_community_local-AS_exact-match;
                    }
                }                  //vpn_all_community_local-AS_exact-match
                leaf vpn_all_community_local-AS_exact-match_wide {
                    type enumeration {
                        enum vpn_all_community_local-AS_exact-match_wide;
                    }
                }                  //wide
                leaf vpn_all_community_local-AS_json {
                    type enumeration {
                        enum vpn_all_community_local-AS_json;
                    }
                }                  //vpn_all_community_local-AS_json
                leaf vpn_all_community_local-AS_json_detail {
                    type enumeration {
                        enum vpn_all_community_local-AS_json_detail;
                    }
                }                  //detail
                leaf vpn_all_community_no-advertise_exact-match {
                    type enumeration {
                        enum vpn_all_community_no-advertise_exact-match;
                    }
                }                  //vpn_all_community_no-advertise_exact-match
                leaf vpn_all_community_no-advertise_exact-match_wide {
                    type enumeration {
                        enum vpn_all_community_no-advertise_exact-match_wide;
                    }
                }                  //wide
                leaf vpn_all_community_no-advertise_json {
                    type enumeration {
                        enum vpn_all_community_no-advertise_json;
                    }
                }                  //vpn_all_community_no-advertise_json
                leaf vpn_all_community_no-advertise_json_detail {
                    type enumeration {
                        enum vpn_all_community_no-advertise_json_detail;
                    }
                }                  //detail
                leaf vpn_all_community_no-export_exact-match {
                    type enumeration {
                        enum vpn_all_community_no-export_exact-match;
                    }
                }                  //vpn_all_community_no-export_exact-match
                leaf vpn_all_community_no-export_exact-match_wide {
                    type enumeration {
                        enum vpn_all_community_no-export_exact-match_wide;
                    }
                }                  //wide
                leaf vpn_all_community_no-export_json {
                    type enumeration {
                        enum vpn_all_community_no-export_json;
                    }
                }                  //vpn_all_community_no-export_json
                leaf vpn_all_community_no-export_json_detail {
                    type enumeration {
                        enum vpn_all_community_no-export_json_detail;
                    }
                }                  //detail
                leaf vpn_all_community_graceful-shutdown_exact-match {
                    type enumeration {
                        enum vpn_all_community_graceful-shutdown_exact-match;
                    }
                }                  //vpn_all_community_graceful-shutdown_exact-match
                leaf vpn_all_community_graceful-shutdown_exact-match_wide {
                    type enumeration {
                        enum vpn_all_community_graceful-shutdown_exact-match_wide;
                    }
                }                  //wide
                leaf vpn_all_community_graceful-shutdown_json {
                    type enumeration {
                        enum vpn_all_community_graceful-shutdown_json;
                    }
                }                  //vpn_all_community_graceful-shutdown_json
                leaf vpn_all_community_graceful-shutdown_json_detail {
                    type enumeration {
                        enum vpn_all_community_graceful-shutdown_json_detail;
                    }
                }                  //detail
                leaf vpn_all_community_no-peer_exact-match {
                    type enumeration {
                        enum vpn_all_community_no-peer_exact-match;
                    }
                }                  //vpn_all_community_no-peer_exact-match
                leaf vpn_all_community_no-peer_exact-match_wide {
                    type enumeration {
                        enum vpn_all_community_no-peer_exact-match_wide;
                    }
                }                  //wide
                leaf vpn_all_community_no-peer_json {
                    type enumeration {
                        enum vpn_all_community_no-peer_json;
                    }
                }                  //vpn_all_community_no-peer_json
                leaf vpn_all_community_no-peer_json_detail {
                    type enumeration {
                        enum vpn_all_community_no-peer_json_detail;
                    }
                }                  //detail
                leaf vpn_all_community_blackhole_exact-match {
                    type enumeration {
                        enum vpn_all_community_blackhole_exact-match;
                    }
                }                  //vpn_all_community_blackhole_exact-match
                leaf vpn_all_community_blackhole_exact-match_wide {
                    type enumeration {
                        enum vpn_all_community_blackhole_exact-match_wide;
                    }
                }                  //wide
                leaf vpn_all_community_blackhole_json {
                    type enumeration {
                        enum vpn_all_community_blackhole_json;
                    }
                }                  //vpn_all_community_blackhole_json
                leaf vpn_all_community_blackhole_json_detail {
                    type enumeration {
                        enum vpn_all_community_blackhole_json_detail;
                    }
                }                  //detail
                leaf vpn_all_community_llgr-stale_exact-match {
                    type enumeration {
                        enum vpn_all_community_llgr-stale_exact-match;
                    }
                }                  //vpn_all_community_llgr-stale_exact-match
                leaf vpn_all_community_llgr-stale_exact-match_wide {
                    type enumeration {
                        enum vpn_all_community_llgr-stale_exact-match_wide;
                    }
                }                  //wide
                leaf vpn_all_community_llgr-stale_json {
                    type enumeration {
                        enum vpn_all_community_llgr-stale_json;
                    }
                }                  //vpn_all_community_llgr-stale_json
                leaf vpn_all_community_llgr-stale_json_detail {
                    type enumeration {
                        enum vpn_all_community_llgr-stale_json_detail;
                    }
                }                  //detail
                leaf vpn_all_community_no-llgr_exact-match {
                    type enumeration {
                        enum vpn_all_community_no-llgr_exact-match;
                    }
                }                  //vpn_all_community_no-llgr_exact-match
                leaf vpn_all_community_no-llgr_exact-match_wide {
                    type enumeration {
                        enum vpn_all_community_no-llgr_exact-match_wide;
                    }
                }                  //wide
                leaf vpn_all_community_no-llgr_json {
                    type enumeration {
                        enum vpn_all_community_no-llgr_json;
                    }
                }                  //vpn_all_community_no-llgr_json
                leaf vpn_all_community_no-llgr_json_detail {
                    type enumeration {
                        enum vpn_all_community_no-llgr_json_detail;
                    }
                }                  //detail
                leaf vpn_all_community_accept-own_exact-match {
                    type enumeration {
                        enum vpn_all_community_accept-own_exact-match;
                    }
                }                  //vpn_all_community_accept-own_exact-match
                leaf vpn_all_community_accept-own_exact-match_wide {
                    type enumeration {
                        enum vpn_all_community_accept-own_exact-match_wide;
                    }
                }                  //wide
                leaf vpn_all_community_accept-own_json {
                    type enumeration {
                        enum vpn_all_community_accept-own_json;
                    }
                }                  //vpn_all_community_accept-own_json
                leaf vpn_all_community_accept-own_json_detail {
                    type enumeration {
                        enum vpn_all_community_accept-own_json_detail;
                    }
                }                  //detail
                leaf vpn_all_community_accept-own-nexthop_exact-match {
                    type enumeration {
                        enum vpn_all_community_accept-own-nexthop_exact-match;
                    }
                }                  //vpn_all_community_accept-own-nexthop_exact-match
                leaf vpn_all_community_accept-own-nexthop_exact-match_wide {
                    type enumeration {
                        enum vpn_all_community_accept-own-nexthop_exact-match_wide;
                    }
                }                  //wide
                leaf vpn_all_community_accept-own-nexthop_json {
                    type enumeration {
                        enum vpn_all_community_accept-own-nexthop_json;
                    }
                }                  //vpn_all_community_accept-own-nexthop_json
                leaf vpn_all_community_accept-own-nexthop_json_detail {
                    type enumeration {
                        enum vpn_all_community_accept-own-nexthop_json_detail;
                    }
                }                  //detail
                leaf vpn_all_community_route-filter-v6_exact-match {
                    type enumeration {
                        enum vpn_all_community_route-filter-v6_exact-match;
                    }
                }                  //vpn_all_community_route-filter-v6_exact-match
                leaf vpn_all_community_route-filter-v6_exact-match_wide {
                    type enumeration {
                        enum vpn_all_community_route-filter-v6_exact-match_wide;
                    }
                }                  //wide
                leaf vpn_all_community_route-filter-v6_json {
                    type enumeration {
                        enum vpn_all_community_route-filter-v6_json;
                    }
                }                  //vpn_all_community_route-filter-v6_json
                leaf vpn_all_community_route-filter-v6_json_detail {
                    type enumeration {
                        enum vpn_all_community_route-filter-v6_json_detail;
                    }
                }                  //detail
                leaf vpn_all_community_route-filter-v4_exact-match {
                    type enumeration {
                        enum vpn_all_community_route-filter-v4_exact-match;
                    }
                }                  //vpn_all_community_route-filter-v4_exact-match
                leaf vpn_all_community_route-filter-v4_exact-match_wide {
                    type enumeration {
                        enum vpn_all_community_route-filter-v4_exact-match_wide;
                    }
                }                  //wide
                leaf vpn_all_community_route-filter-v4_json {
                    type enumeration {
                        enum vpn_all_community_route-filter-v4_json;
                    }
                }                  //vpn_all_community_route-filter-v4_json
                leaf vpn_all_community_route-filter-v4_json_detail {
                    type enumeration {
                        enum vpn_all_community_route-filter-v4_json_detail;
                    }
                }                  //detail
                leaf vpn_all_community_route-filter-translated-v6_exact-match {
                    type enumeration {
                        enum vpn_all_community_route-filter-translated-v6_exact-match;
                    }
                }                  //vpn_all_community_route-filter-translated-v6_exact-match
                leaf vpn_all_community_route-filter-translated-v6_exact-match_wide {
                    type enumeration {
                        enum vpn_all_community_route-filter-translated-v6_exact-match_wide;
                    }
                }                  //wide
                leaf vpn_all_community_route-filter-translated-v6_json {
                    type enumeration {
                        enum vpn_all_community_route-filter-translated-v6_json;
                    }
                }                  //vpn_all_community_route-filter-translated-v6_json
                leaf vpn_all_community_route-filter-translated-v6_json_detail {
                    type enumeration {
                        enum vpn_all_community_route-filter-translated-v6_json_detail;
                    }
                }                  //detail
                leaf vpn_all_community_route-filter-translated-v4_exact-match {
                    type enumeration {
                        enum vpn_all_community_route-filter-translated-v4_exact-match;
                    }
                }                  //vpn_all_community_route-filter-translated-v4_exact-match
                leaf vpn_all_community_route-filter-translated-v4_exact-match_wide {
                    type enumeration {
                        enum vpn_all_community_route-filter-translated-v4_exact-match_wide;
                    }
                }                  //wide
                leaf vpn_all_community_route-filter-translated-v4_json {
                    type enumeration {
                        enum vpn_all_community_route-filter-translated-v4_json;
                    }
                }                  //vpn_all_community_route-filter-translated-v4_json
                leaf vpn_all_community_route-filter-translated-v4_json_detail {
                    type enumeration {
                        enum vpn_all_community_route-filter-translated-v4_json_detail;
                    }
                }                  //detail
                leaf vpn_all_community_exact-match_json {
                    type enumeration {
                        enum vpn_all_community_exact-match_json;
                    }
                }                  //vpn_all_community_exact-match_json
                leaf vpn_all_community_exact-match_json_detail {
                    type enumeration {
                        enum vpn_all_community_exact-match_json_detail;
                    }
                }                  //detail
                leaf vpn_all_summary_established_terse {
                    type enumeration {
                        enum vpn_all_summary_established_terse;
                    }
                }                  //vpn_all_summary_established_terse
                leaf vpn_all_summary_established_terse_json {
                    type enumeration {
                        enum vpn_all_summary_established_terse_json;
                    }
                }                  //json
                leaf vpn_all_summary_established_wide {
                    type enumeration {
                        enum vpn_all_summary_established_wide;
                    }
                }                  //vpn_all_summary_established_wide
                leaf vpn_all_summary_established_wide_json {
                    type enumeration {
                        enum vpn_all_summary_established_wide_json;
                    }
                }                  //json
                leaf vpn_all_summary_failed_terse {
                    type enumeration {
                        enum vpn_all_summary_failed_terse;
                    }
                }                  //vpn_all_summary_failed_terse
                leaf vpn_all_summary_failed_terse_json {
                    type enumeration {
                        enum vpn_all_summary_failed_terse_json;
                    }
                }                  //json
                leaf vpn_all_summary_failed_wide {
                    type enumeration {
                        enum vpn_all_summary_failed_wide;
                    }
                }                  //vpn_all_summary_failed_wide
                leaf vpn_all_summary_failed_wide_json {
                    type enumeration {
                        enum vpn_all_summary_failed_wide_json;
                    }
                }                  //json
                leaf vpn_all_summary_terse_wide {
                    type enumeration {
                        enum vpn_all_summary_terse_wide;
                    }
                }                  //vpn_all_summary_terse_wide
                leaf vpn_all_summary_terse_wide_json {
                    type enumeration {
                        enum vpn_all_summary_terse_wide_json;
                    }
                }                  //json
                leaf vpn_community_local-AS_exact-match_json {
                    type enumeration {
                        enum vpn_community_local-AS_exact-match_json;
                    }
                }                  //vpn_community_local-AS_exact-match_json
                leaf vpn_community_local-AS_exact-match_json_detail {
                    type enumeration {
                        enum vpn_community_local-AS_exact-match_json_detail;
                    }
                }                  //detail
                leaf vpn_community_no-advertise_exact-match_json {
                    type enumeration {
                        enum vpn_community_no-advertise_exact-match_json;
                    }
                }                  //vpn_community_no-advertise_exact-match_json
                leaf vpn_community_no-advertise_exact-match_json_detail {
                    type enumeration {
                        enum vpn_community_no-advertise_exact-match_json_detail;
                    }
                }                  //detail
                leaf vpn_community_no-export_exact-match_json {
                    type enumeration {
                        enum vpn_community_no-export_exact-match_json;
                    }
                }                  //vpn_community_no-export_exact-match_json
                leaf vpn_community_no-export_exact-match_json_detail {
                    type enumeration {
                        enum vpn_community_no-export_exact-match_json_detail;
                    }
                }                  //detail
                leaf vpn_community_graceful-shutdown_exact-match_json {
                    type enumeration {
                        enum vpn_community_graceful-shutdown_exact-match_json;
                    }
                }                  //vpn_community_graceful-shutdown_exact-match_json
                leaf vpn_community_graceful-shutdown_exact-match_json_detail {
                    type enumeration {
                        enum vpn_community_graceful-shutdown_exact-match_json_detail;
                    }
                }                  //detail
                leaf vpn_community_no-peer_exact-match_json {
                    type enumeration {
                        enum vpn_community_no-peer_exact-match_json;
                    }
                }                  //vpn_community_no-peer_exact-match_json
                leaf vpn_community_no-peer_exact-match_json_detail {
                    type enumeration {
                        enum vpn_community_no-peer_exact-match_json_detail;
                    }
                }                  //detail
                leaf vpn_community_blackhole_exact-match_json {
                    type enumeration {
                        enum vpn_community_blackhole_exact-match_json;
                    }
                }                  //vpn_community_blackhole_exact-match_json
                leaf vpn_community_blackhole_exact-match_json_detail {
                    type enumeration {
                        enum vpn_community_blackhole_exact-match_json_detail;
                    }
                }                  //detail
                leaf vpn_community_llgr-stale_exact-match_json {
                    type enumeration {
                        enum vpn_community_llgr-stale_exact-match_json;
                    }
                }                  //vpn_community_llgr-stale_exact-match_json
                leaf vpn_community_llgr-stale_exact-match_json_detail {
                    type enumeration {
                        enum vpn_community_llgr-stale_exact-match_json_detail;
                    }
                }                  //detail
                leaf vpn_community_no-llgr_exact-match_json {
                    type enumeration {
                        enum vpn_community_no-llgr_exact-match_json;
                    }
                }                  //vpn_community_no-llgr_exact-match_json
                leaf vpn_community_no-llgr_exact-match_json_detail {
                    type enumeration {
                        enum vpn_community_no-llgr_exact-match_json_detail;
                    }
                }                  //detail
                leaf vpn_community_accept-own_exact-match_json {
                    type enumeration {
                        enum vpn_community_accept-own_exact-match_json;
                    }
                }                  //vpn_community_accept-own_exact-match_json
                leaf vpn_community_accept-own_exact-match_json_detail {
                    type enumeration {
                        enum vpn_community_accept-own_exact-match_json_detail;
                    }
                }                  //detail
                leaf vpn_community_accept-own-nexthop_exact-match_json {
                    type enumeration {
                        enum vpn_community_accept-own-nexthop_exact-match_json;
                    }
                }                  //vpn_community_accept-own-nexthop_exact-match_json
                leaf vpn_community_accept-own-nexthop_exact-match_json_detail {
                    type enumeration {
                        enum vpn_community_accept-own-nexthop_exact-match_json_detail;
                    }
                }                  //detail
                leaf vpn_community_route-filter-v6_exact-match_json {
                    type enumeration {
                        enum vpn_community_route-filter-v6_exact-match_json;
                    }
                }                  //vpn_community_route-filter-v6_exact-match_json
                leaf vpn_community_route-filter-v6_exact-match_json_detail {
                    type enumeration {
                        enum vpn_community_route-filter-v6_exact-match_json_detail;
                    }
                }                  //detail
                leaf vpn_community_route-filter-v4_exact-match_json {
                    type enumeration {
                        enum vpn_community_route-filter-v4_exact-match_json;
                    }
                }                  //vpn_community_route-filter-v4_exact-match_json
                leaf vpn_community_route-filter-v4_exact-match_json_detail {
                    type enumeration {
                        enum vpn_community_route-filter-v4_exact-match_json_detail;
                    }
                }                  //detail
                leaf vpn_community_route-filter-translated-v6_exact-match_json {
                    type enumeration {
                        enum vpn_community_route-filter-translated-v6_exact-match_json;
                    }
                }                  //vpn_community_route-filter-translated-v6_exact-match_json
                leaf vpn_community_route-filter-translated-v6_exact-match_json_detail {
                    type enumeration {
                        enum vpn_community_route-filter-translated-v6_exact-match_json_detail;
                    }
                }                  //detail
                leaf vpn_community_route-filter-translated-v4_exact-match_json {
                    type enumeration {
                        enum vpn_community_route-filter-translated-v4_exact-match_json;
                    }
                }                  //vpn_community_route-filter-translated-v4_exact-match_json
                leaf vpn_community_route-filter-translated-v4_exact-match_json_detail {
                    type enumeration {
                        enum vpn_community_route-filter-translated-v4_exact-match_json_detail;
                    }
                }                  //detail
                leaf vpn_summary_established_terse_wide {
                    type enumeration {
                        enum vpn_summary_established_terse_wide;
                    }
                }                  //vpn_summary_established_terse_wide
                leaf vpn_summary_established_terse_wide_json {
                    type enumeration {
                        enum vpn_summary_established_terse_wide_json;
                    }
                }                  //json
                leaf vpn_summary_failed_terse_wide {
                    type enumeration {
                        enum vpn_summary_failed_terse_wide;
                    }
                }                  //vpn_summary_failed_terse_wide
                leaf vpn_summary_failed_terse_wide_json {
                    type enumeration {
                        enum vpn_summary_failed_terse_wide_json;
                    }
                }                  //json
                leaf unicast_all_community_local-AS_exact-match_json {
                    type enumeration {
                        enum unicast_all_community_local-AS_exact-match_json;
                    }
                }                  //unicast_all_community_local-AS_exact-match_json
                leaf unicast_all_community_local-AS_exact-match_json_detail {
                    type enumeration {
                        enum unicast_all_community_local-AS_exact-match_json_detail;
                    }
                }                  //detail
                leaf unicast_all_community_no-advertise_exact-match_json {
                    type enumeration {
                        enum unicast_all_community_no-advertise_exact-match_json;
                    }
                }                  //unicast_all_community_no-advertise_exact-match_json
                leaf unicast_all_community_no-advertise_exact-match_json_detail {
                    type enumeration {
                        enum unicast_all_community_no-advertise_exact-match_json_detail;
                    }
                }                  //detail
                leaf unicast_all_community_no-export_exact-match_json {
                    type enumeration {
                        enum unicast_all_community_no-export_exact-match_json;
                    }
                }                  //unicast_all_community_no-export_exact-match_json
                leaf unicast_all_community_no-export_exact-match_json_detail {
                    type enumeration {
                        enum unicast_all_community_no-export_exact-match_json_detail;
                    }
                }                  //detail
                leaf unicast_all_community_graceful-shutdown_exact-match_json {
                    type enumeration {
                        enum unicast_all_community_graceful-shutdown_exact-match_json;
                    }
                }                  //unicast_all_community_graceful-shutdown_exact-match_json
                leaf unicast_all_community_graceful-shutdown_exact-match_json_detail {
                    type enumeration {
                        enum unicast_all_community_graceful-shutdown_exact-match_json_detail;
                    }
                }                  //detail
                leaf unicast_all_community_no-peer_exact-match_json {
                    type enumeration {
                        enum unicast_all_community_no-peer_exact-match_json;
                    }
                }                  //unicast_all_community_no-peer_exact-match_json
                leaf unicast_all_community_no-peer_exact-match_json_detail {
                    type enumeration {
                        enum unicast_all_community_no-peer_exact-match_json_detail;
                    }
                }                  //detail
                leaf unicast_all_community_blackhole_exact-match_json {
                    type enumeration {
                        enum unicast_all_community_blackhole_exact-match_json;
                    }
                }                  //unicast_all_community_blackhole_exact-match_json
                leaf unicast_all_community_blackhole_exact-match_json_detail {
                    type enumeration {
                        enum unicast_all_community_blackhole_exact-match_json_detail;
                    }
                }                  //detail
                leaf unicast_all_community_llgr-stale_exact-match_json {
                    type enumeration {
                        enum unicast_all_community_llgr-stale_exact-match_json;
                    }
                }                  //unicast_all_community_llgr-stale_exact-match_json
                leaf unicast_all_community_llgr-stale_exact-match_json_detail {
                    type enumeration {
                        enum unicast_all_community_llgr-stale_exact-match_json_detail;
                    }
                }                  //detail
                leaf unicast_all_community_no-llgr_exact-match_json {
                    type enumeration {
                        enum unicast_all_community_no-llgr_exact-match_json;
                    }
                }                  //unicast_all_community_no-llgr_exact-match_json
                leaf unicast_all_community_no-llgr_exact-match_json_detail {
                    type enumeration {
                        enum unicast_all_community_no-llgr_exact-match_json_detail;
                    }
                }                  //detail
                leaf unicast_all_community_accept-own_exact-match_json {
                    type enumeration {
                        enum unicast_all_community_accept-own_exact-match_json;
                    }
                }                  //unicast_all_community_accept-own_exact-match_json
                leaf unicast_all_community_accept-own_exact-match_json_detail {
                    type enumeration {
                        enum unicast_all_community_accept-own_exact-match_json_detail;
                    }
                }                  //detail
                leaf unicast_all_community_accept-own-nexthop_exact-match_json {
                    type enumeration {
                        enum unicast_all_community_accept-own-nexthop_exact-match_json;
                    }
                }                  //unicast_all_community_accept-own-nexthop_exact-match_json
                leaf unicast_all_community_accept-own-nexthop_exact-match_json_detail {
                    type enumeration {
                        enum unicast_all_community_accept-own-nexthop_exact-match_json_detail;
                    }
                }                  //detail
                leaf unicast_all_community_route-filter-v6_exact-match_json {
                    type enumeration {
                        enum unicast_all_community_route-filter-v6_exact-match_json;
                    }
                }                  //unicast_all_community_route-filter-v6_exact-match_json
                leaf unicast_all_community_route-filter-v6_exact-match_json_detail {
                    type enumeration {
                        enum unicast_all_community_route-filter-v6_exact-match_json_detail;
                    }
                }                  //detail
                leaf unicast_all_community_route-filter-v4_exact-match_json {
                    type enumeration {
                        enum unicast_all_community_route-filter-v4_exact-match_json;
                    }
                }                  //unicast_all_community_route-filter-v4_exact-match_json
                leaf unicast_all_community_route-filter-v4_exact-match_json_detail {
                    type enumeration {
                        enum unicast_all_community_route-filter-v4_exact-match_json_detail;
                    }
                }                  //detail
                leaf unicast_all_community_route-filter-translated-v6_exact-match_json {
                    type enumeration {
                        enum unicast_all_community_route-filter-translated-v6_exact-match_json;
                    }
                }                  //unicast_all_community_route-filter-translated-v6_exact-match_json
                leaf unicast_all_community_route-filter-translated-v6_exact-match_json_detail {
                    type enumeration {
                        enum unicast_all_community_route-filter-translated-v6_exact-match_json_detail;
                    }
                }                  //detail
                leaf unicast_all_community_route-filter-translated-v4_exact-match_json {
                    type enumeration {
                        enum unicast_all_community_route-filter-translated-v4_exact-match_json;
                    }
                }                  //unicast_all_community_route-filter-translated-v4_exact-match_json
                leaf unicast_all_community_route-filter-translated-v4_exact-match_json_detail {
                    type enumeration {
                        enum unicast_all_community_route-filter-translated-v4_exact-match_json_detail;
                    }
                }                  //detail
                leaf unicast_all_summary_established_terse_wide {
                    type enumeration {
                        enum unicast_all_summary_established_terse_wide;
                    }
                }                  //unicast_all_summary_established_terse_wide
                leaf unicast_all_summary_established_terse_wide_json {
                    type enumeration {
                        enum unicast_all_summary_established_terse_wide_json;
                    }
                }                  //json
                leaf unicast_all_summary_failed_terse_wide {
                    type enumeration {
                        enum unicast_all_summary_failed_terse_wide;
                    }
                }                  //unicast_all_summary_failed_terse_wide
                leaf unicast_all_summary_failed_terse_wide_json {
                    type enumeration {
                        enum unicast_all_summary_failed_terse_wide_json;
                    }
                }                  //json
                leaf flowspec_all_community_local-AS_exact-match_json {
                    type enumeration {
                        enum flowspec_all_community_local-AS_exact-match_json;
                    }
                }                  //flowspec_all_community_local-AS_exact-match_json
                leaf flowspec_all_community_local-AS_exact-match_json_detail {
                    type enumeration {
                        enum flowspec_all_community_local-AS_exact-match_json_detail;
                    }
                }                  //detail
                leaf flowspec_all_community_no-advertise_exact-match_json {
                    type enumeration {
                        enum flowspec_all_community_no-advertise_exact-match_json;
                    }
                }                  //flowspec_all_community_no-advertise_exact-match_json
                leaf flowspec_all_community_no-advertise_exact-match_json_detail {
                    type enumeration {
                        enum flowspec_all_community_no-advertise_exact-match_json_detail;
                    }
                }                  //detail
                leaf flowspec_all_community_no-export_exact-match_json {
                    type enumeration {
                        enum flowspec_all_community_no-export_exact-match_json;
                    }
                }                  //flowspec_all_community_no-export_exact-match_json
                leaf flowspec_all_community_no-export_exact-match_json_detail {
                    type enumeration {
                        enum flowspec_all_community_no-export_exact-match_json_detail;
                    }
                }                  //detail
                leaf flowspec_all_community_graceful-shutdown_exact-match_json {
                    type enumeration {
                        enum flowspec_all_community_graceful-shutdown_exact-match_json;
                    }
                }                  //flowspec_all_community_graceful-shutdown_exact-match_json
                leaf flowspec_all_community_graceful-shutdown_exact-match_json_detail {
                    type enumeration {
                        enum flowspec_all_community_graceful-shutdown_exact-match_json_detail;
                    }
                }                  //detail
                leaf flowspec_all_community_no-peer_exact-match_json {
                    type enumeration {
                        enum flowspec_all_community_no-peer_exact-match_json;
                    }
                }                  //flowspec_all_community_no-peer_exact-match_json
                leaf flowspec_all_community_no-peer_exact-match_json_detail {
                    type enumeration {
                        enum flowspec_all_community_no-peer_exact-match_json_detail;
                    }
                }                  //detail
                leaf flowspec_all_community_blackhole_exact-match_json {
                    type enumeration {
                        enum flowspec_all_community_blackhole_exact-match_json;
                    }
                }                  //flowspec_all_community_blackhole_exact-match_json
                leaf flowspec_all_community_blackhole_exact-match_json_detail {
                    type enumeration {
                        enum flowspec_all_community_blackhole_exact-match_json_detail;
                    }
                }                  //detail
                leaf flowspec_all_community_llgr-stale_exact-match_json {
                    type enumeration {
                        enum flowspec_all_community_llgr-stale_exact-match_json;
                    }
                }                  //flowspec_all_community_llgr-stale_exact-match_json
                leaf flowspec_all_community_llgr-stale_exact-match_json_detail {
                    type enumeration {
                        enum flowspec_all_community_llgr-stale_exact-match_json_detail;
                    }
                }                  //detail
                leaf flowspec_all_community_no-llgr_exact-match_json {
                    type enumeration {
                        enum flowspec_all_community_no-llgr_exact-match_json;
                    }
                }                  //flowspec_all_community_no-llgr_exact-match_json
                leaf flowspec_all_community_no-llgr_exact-match_json_detail {
                    type enumeration {
                        enum flowspec_all_community_no-llgr_exact-match_json_detail;
                    }
                }                  //detail
                leaf flowspec_all_community_accept-own_exact-match_json {
                    type enumeration {
                        enum flowspec_all_community_accept-own_exact-match_json;
                    }
                }                  //flowspec_all_community_accept-own_exact-match_json
                leaf flowspec_all_community_accept-own_exact-match_json_detail {
                    type enumeration {
                        enum flowspec_all_community_accept-own_exact-match_json_detail;
                    }
                }                  //detail
                leaf flowspec_all_community_accept-own-nexthop_exact-match_json {
                    type enumeration {
                        enum flowspec_all_community_accept-own-nexthop_exact-match_json;
                    }
                }                  //flowspec_all_community_accept-own-nexthop_exact-match_json
                leaf flowspec_all_community_accept-own-nexthop_exact-match_json_detail {
                    type enumeration {
                        enum flowspec_all_community_accept-own-nexthop_exact-match_json_detail;
                    }
                }                  //detail
                leaf flowspec_all_community_route-filter-v6_exact-match_json {
                    type enumeration {
                        enum flowspec_all_community_route-filter-v6_exact-match_json;
                    }
                }                  //flowspec_all_community_route-filter-v6_exact-match_json
                leaf flowspec_all_community_route-filter-v6_exact-match_json_detail {
                    type enumeration {
                        enum flowspec_all_community_route-filter-v6_exact-match_json_detail;
                    }
                }                  //detail
                leaf flowspec_all_community_route-filter-v4_exact-match_json {
                    type enumeration {
                        enum flowspec_all_community_route-filter-v4_exact-match_json;
                    }
                }                  //flowspec_all_community_route-filter-v4_exact-match_json
                leaf flowspec_all_community_route-filter-v4_exact-match_json_detail {
                    type enumeration {
                        enum flowspec_all_community_route-filter-v4_exact-match_json_detail;
                    }
                }                  //detail
                leaf flowspec_all_community_route-filter-translated-v6_exact-match_json {
                    type enumeration {
                        enum flowspec_all_community_route-filter-translated-v6_exact-match_json;
                    }
                }                  //flowspec_all_community_route-filter-translated-v6_exact-match_json
                leaf flowspec_all_community_route-filter-translated-v6_exact-match_json_detail {
                    type enumeration {
                        enum flowspec_all_community_route-filter-translated-v6_exact-match_json_detail;
                    }
                }                  //detail
                leaf flowspec_all_community_route-filter-translated-v4_exact-match_json {
                    type enumeration {
                        enum flowspec_all_community_route-filter-translated-v4_exact-match_json;
                    }
                }                  //flowspec_all_community_route-filter-translated-v4_exact-match_json
                leaf flowspec_all_community_route-filter-translated-v4_exact-match_json_detail {
                    type enumeration {
                        enum flowspec_all_community_route-filter-translated-v4_exact-match_json_detail;
                    }
                }                  //detail
                leaf flowspec_all_summary_established_terse_wide {
                    type enumeration {
                        enum flowspec_all_summary_established_terse_wide;
                    }
                }                  //flowspec_all_summary_established_terse_wide
                leaf flowspec_all_summary_established_terse_wide_json {
                    type enumeration {
                        enum flowspec_all_summary_established_terse_wide_json;
                    }
                }                  //json
                leaf flowspec_all_summary_failed_terse_wide {
                    type enumeration {
                        enum flowspec_all_summary_failed_terse_wide;
                    }
                }                  //flowspec_all_summary_failed_terse_wide
                leaf flowspec_all_summary_failed_terse_wide_json {
                    type enumeration {
                        enum flowspec_all_summary_failed_terse_wide_json;
                    }
                }                  //json
                leaf vpn_all_community_local-AS_exact-match_json {
                    type enumeration {
                        enum vpn_all_community_local-AS_exact-match_json;
                    }
                }                  //vpn_all_community_local-AS_exact-match_json
                leaf vpn_all_community_local-AS_exact-match_json_detail {
                    type enumeration {
                        enum vpn_all_community_local-AS_exact-match_json_detail;
                    }
                }                  //detail
                leaf vpn_all_community_no-advertise_exact-match_json {
                    type enumeration {
                        enum vpn_all_community_no-advertise_exact-match_json;
                    }
                }                  //vpn_all_community_no-advertise_exact-match_json
                leaf vpn_all_community_no-advertise_exact-match_json_detail {
                    type enumeration {
                        enum vpn_all_community_no-advertise_exact-match_json_detail;
                    }
                }                  //detail
                leaf vpn_all_community_no-export_exact-match_json {
                    type enumeration {
                        enum vpn_all_community_no-export_exact-match_json;
                    }
                }                  //vpn_all_community_no-export_exact-match_json
                leaf vpn_all_community_no-export_exact-match_json_detail {
                    type enumeration {
                        enum vpn_all_community_no-export_exact-match_json_detail;
                    }
                }                  //detail
                leaf vpn_all_community_graceful-shutdown_exact-match_json {
                    type enumeration {
                        enum vpn_all_community_graceful-shutdown_exact-match_json;
                    }
                }                  //vpn_all_community_graceful-shutdown_exact-match_json
                leaf vpn_all_community_graceful-shutdown_exact-match_json_detail {
                    type enumeration {
                        enum vpn_all_community_graceful-shutdown_exact-match_json_detail;
                    }
                }                  //detail
                leaf vpn_all_community_no-peer_exact-match_json {
                    type enumeration {
                        enum vpn_all_community_no-peer_exact-match_json;
                    }
                }                  //vpn_all_community_no-peer_exact-match_json
                leaf vpn_all_community_no-peer_exact-match_json_detail {
                    type enumeration {
                        enum vpn_all_community_no-peer_exact-match_json_detail;
                    }
                }                  //detail
                leaf vpn_all_community_blackhole_exact-match_json {
                    type enumeration {
                        enum vpn_all_community_blackhole_exact-match_json;
                    }
                }                  //vpn_all_community_blackhole_exact-match_json
                leaf vpn_all_community_blackhole_exact-match_json_detail {
                    type enumeration {
                        enum vpn_all_community_blackhole_exact-match_json_detail;
                    }
                }                  //detail
                leaf vpn_all_community_llgr-stale_exact-match_json {
                    type enumeration {
                        enum vpn_all_community_llgr-stale_exact-match_json;
                    }
                }                  //vpn_all_community_llgr-stale_exact-match_json
                leaf vpn_all_community_llgr-stale_exact-match_json_detail {
                    type enumeration {
                        enum vpn_all_community_llgr-stale_exact-match_json_detail;
                    }
                }                  //detail
                leaf vpn_all_community_no-llgr_exact-match_json {
                    type enumeration {
                        enum vpn_all_community_no-llgr_exact-match_json;
                    }
                }                  //vpn_all_community_no-llgr_exact-match_json
                leaf vpn_all_community_no-llgr_exact-match_json_detail {
                    type enumeration {
                        enum vpn_all_community_no-llgr_exact-match_json_detail;
                    }
                }                  //detail
                leaf vpn_all_community_accept-own_exact-match_json {
                    type enumeration {
                        enum vpn_all_community_accept-own_exact-match_json;
                    }
                }                  //vpn_all_community_accept-own_exact-match_json
                leaf vpn_all_community_accept-own_exact-match_json_detail {
                    type enumeration {
                        enum vpn_all_community_accept-own_exact-match_json_detail;
                    }
                }                  //detail
                leaf vpn_all_community_accept-own-nexthop_exact-match_json {
                    type enumeration {
                        enum vpn_all_community_accept-own-nexthop_exact-match_json;
                    }
                }                  //vpn_all_community_accept-own-nexthop_exact-match_json
                leaf vpn_all_community_accept-own-nexthop_exact-match_json_detail {
                    type enumeration {
                        enum vpn_all_community_accept-own-nexthop_exact-match_json_detail;
                    }
                }                  //detail
                leaf vpn_all_community_route-filter-v6_exact-match_json {
                    type enumeration {
                        enum vpn_all_community_route-filter-v6_exact-match_json;
                    }
                }                  //vpn_all_community_route-filter-v6_exact-match_json
                leaf vpn_all_community_route-filter-v6_exact-match_json_detail {
                    type enumeration {
                        enum vpn_all_community_route-filter-v6_exact-match_json_detail;
                    }
                }                  //detail
                leaf vpn_all_community_route-filter-v4_exact-match_json {
                    type enumeration {
                        enum vpn_all_community_route-filter-v4_exact-match_json;
                    }
                }                  //vpn_all_community_route-filter-v4_exact-match_json
                leaf vpn_all_community_route-filter-v4_exact-match_json_detail {
                    type enumeration {
                        enum vpn_all_community_route-filter-v4_exact-match_json_detail;
                    }
                }                  //detail
                leaf vpn_all_community_route-filter-translated-v6_exact-match_json {
                    type enumeration {
                        enum vpn_all_community_route-filter-translated-v6_exact-match_json;
                    }
                }                  //vpn_all_community_route-filter-translated-v6_exact-match_json
                leaf vpn_all_community_route-filter-translated-v6_exact-match_json_detail {
                    type enumeration {
                        enum vpn_all_community_route-filter-translated-v6_exact-match_json_detail;
                    }
                }                  //detail
                leaf vpn_all_community_route-filter-translated-v4_exact-match_json {
                    type enumeration {
                        enum vpn_all_community_route-filter-translated-v4_exact-match_json;
                    }
                }                  //vpn_all_community_route-filter-translated-v4_exact-match_json
                leaf vpn_all_community_route-filter-translated-v4_exact-match_json_detail {
                    type enumeration {
                        enum vpn_all_community_route-filter-translated-v4_exact-match_json_detail;
                    }
                }                  //detail
                leaf vpn_all_summary_established_terse_wide {
                    type enumeration {
                        enum vpn_all_summary_established_terse_wide;
                    }
                }                  //vpn_all_summary_established_terse_wide
                leaf vpn_all_summary_established_terse_wide_json {
                    type enumeration {
                        enum vpn_all_summary_established_terse_wide_json;
                    }
                }                  //json
                leaf vpn_all_summary_failed_terse_wide {
                    type enumeration {
                        enum vpn_all_summary_failed_terse_wide;
                    }
                }                  //vpn_all_summary_failed_terse_wide
                leaf vpn_all_summary_failed_terse_wide_json {
                    type enumeration {
                        enum vpn_all_summary_failed_terse_wide_json;
                    }
                }                  //json
                leaf attribute-info {
                    type enumeration {
                        enum attribute-info;
                    }
                }                  //attribute-info
                leaf community-info {
                    type enumeration {
                        enum community-info;
                    }
                }                  //community-info
                leaf memory {
                    type enumeration {
                        enum memory;
                    }
                }                  //memory
                leaf views {
                    type enumeration {
                        enum views;
                    }
                }                  //views
                leaf listeners {
                    type enumeration {
                        enum listeners;
                    }
                }                  //listeners
                leaf peerhash {
                    type enumeration {
                        enum peerhash;
                    }
                }                  //peerhash
                leaf INSTANCE_VIEW_VRF {
                    type enumeration {
                        enum view;
                        enum vrf;
                    }
                }                  //<view|vrf> ['BGP view', 'BGP VRF']
                leaf VIEWVRF_NAME {
                    type string;
                }                  //VIEWVRFNAME
            }
            container show_router-id {
                leaf vrf {
                    type enumeration {
                        enum vrf;
                    }
                }                  //vrf
                leaf THE_VRF_NAME {
                    type string;
                }                  //NAME
            }
            container show_babel {
                leaf parameters {
                    type enumeration {
                        enum parameters;
                    }
                }                  //parameters
            }
            container show_cli {
                leaf graph {
                    type enumeration {
                        enum graph;
                    }
                }                  //graph
            }
            container show_commandtree {
                leaf permutations {
                    type enumeration {
                        enum permutations;
                    }
                }                  //permutations
            }
            container show_configuration {
                leaf compare {
                    type enumeration {
                        enum compare;
                    }
                }                  //compare
                leaf transaction {
                    type int32;
                }                  //(1-4294967295)
                leaf CONFIGURATION_STATE {
                    type enumeration {
                        enum candidate;
                        enum running;
                    }
                }                  //<candidate|running> ['Candidate configuration', 'Running configuration', 'Configuration transaction', 'Transaction ID']
                leaf OUTPUT_FORMAT {
                    type enumeration {
                        enum json;
                        enum xml;
                    }
                }                  //<json|xml> ['Change output format to JSON', 'Change output format to XML']
                leaf translate {
                    type enumeration {
                        enum translate;
                    }
                }                  //translate
                leaf YANG_MODULE_TRANSLATOR {
                    type string;
                }                  //WORD
            }
            container show_dmvpn {
                leaf json {
                    type enumeration {
                        enum json;
                    }
                }                  //json
            }
            container show_evpn {
                leaf json {
                    type enumeration {
                        enum json;
                    }
                }                  //json
            }
            container show_interface {
                leaf INTERFACE_NAME {
                    type string;
                }                  //IFNAME
                leaf vrf {
                    type enumeration {
                        enum vrf;
                    }
                }                  //vrf
                leaf THE_VRF_NAME {
                    type string;
                }                  //NAME
                leaf json {
                    type enumeration {
                        enum json;
                    }
                }                  //json
                leaf nexthop-group {
                    type enumeration {
                        enum nexthop-group;
                    }
                }                  //nexthop-group
                leaf vrf_all {
                    type enumeration {
                        enum vrf_all;
                    }
                }                  //vrf_all
                leaf vrf_all_json {
                    type enumeration {
                        enum vrf_all_json;
                    }
                }                  //json
            }
            container show_isis {
                leaf vrf {
                    type enumeration {
                        enum vrf;
                    }
                }                  //vrf
                leaf THE_VRF_NAME {
                    type string;
                }                  //NAME
                leaf all {
                    type enumeration {
                        enum all;
                    }
                }
                leaf database {
                    type enumeration {
                        enum database;
                    }
                }                  //database
                leaf database_json {
                    type enumeration {
                        enum database_json;
                    }
                }                  //json
                leaf fast-reroute_summary {
                    type enumeration {
                        enum fast-reroute_summary;
                    }
                }                  //summary
                leaf hostname {
                    type enumeration {
                        enum hostname;
                    }
                }                  //hostname
                leaf interface {
                    type enumeration {
                        enum interface;
                    }
                }                  //interface
                leaf interface_json {
                    type enumeration {
                        enum interface_json;
                    }
                }                  //json
                leaf mpls-te_router {
                    type enumeration {
                        enum mpls-te_router;
                    }
                }                  //router
                leaf neighbor {
                    type enumeration {
                        enum neighbor;
                    }
                }                  //neighbor
                leaf neighbor_json {
                    type enumeration {
                        enum neighbor_json;
                    }
                }                  //json
                leaf route {
                    type enumeration {
                        enum route;
                    }
                }                  //route
                leaf spf-delay-ietf {
                    type enumeration {
                        enum spf-delay-ietf;
                    }
                }                  //spf-delay-ietf
                leaf summary {
                    type enumeration {
                        enum summary;
                    }
                }                  //summary
                leaf summary_json {
                    type enumeration {
                        enum summary_json;
                    }
                }                  //json
                leaf topology {
                    type enumeration {
                        enum topology;
                    }
                }                  //topology
                leaf database_detail {
                    type enumeration {
                        enum database_detail;
                    }
                }                  //database_detail
                leaf database_detail_json {
                    type enumeration {
                        enum database_detail_json;
                    }
                }                  //json
                leaf interface_detail {
                    type enumeration {
                        enum interface_detail;
                    }
                }                  //interface_detail
                leaf interface_detail_json {
                    type enumeration {
                        enum interface_detail_json;
                    }
                }                  //json
                leaf mpls-te_database {
                    type enumeration {
                        enum mpls-te_database;
                    }
                }                  //mpls-te_database
                leaf mpls-te_database_detail {
                    type enumeration {
                        enum mpls-te_database_detail;
                    }
                }                  //detail
                leaf mpls-te_database_json {
                    type enumeration {
                        enum mpls-te_database_json;
                    }
                }                  //json
                leaf neighbor_detail {
                    type enumeration {
                        enum neighbor_detail;
                    }
                }                  //neighbor_detail
                leaf neighbor_detail_json {
                    type enumeration {
                        enum neighbor_detail_json;
                    }
                }                  //json
                leaf mpls-te_database_vertex {
                    type enumeration {
                        enum mpls-te_database_vertex;
                    }
                }                  //mpls-te_database_vertex
                leaf mpls-te_database_vertex_detail {
                    type enumeration {
                        enum mpls-te_database_vertex_detail;
                    }
                }                  //detail
                leaf mpls-te_database_vertex_json {
                    type enumeration {
                        enum mpls-te_database_vertex_json;
                    }
                }                  //json
                leaf mpls-te_database_edge {
                    type enumeration {
                        enum mpls-te_database_edge;
                    }
                }                  //mpls-te_database_edge
                leaf mpls-te_database_edge_detail {
                    type enumeration {
                        enum mpls-te_database_edge_detail;
                    }
                }                  //detail
                leaf mpls-te_database_edge_json {
                    type enumeration {
                        enum mpls-te_database_edge_json;
                    }
                }                  //json
                leaf mpls-te_database_subnet {
                    type enumeration {
                        enum mpls-te_database_subnet;
                    }
                }                  //mpls-te_database_subnet
                leaf mpls-te_database_subnet_detail {
                    type enumeration {
                        enum mpls-te_database_subnet_detail;
                    }
                }                  //detail
                leaf mpls-te_database_subnet_json {
                    type enumeration {
                        enum mpls-te_database_subnet_json;
                    }
                }                  //json
            }
            container show_logging {
                leaf filter-text {
                    type enumeration {
                        enum filter-text;
                    }
                }                  //filter-text
            }
            container show_memory {
                leaf DAEMONS_LIST {
                    type enumeration {
                        enum babeld;
                        enum bgpd;
                        enum fabricd;
                        enum ldpd;
                        enum ospfd;
                        enum pbrd;
                        enum pimd;
                        enum ripngd;
                        enum vrrpd;
                        enum bfdd;
                        enum eigrpd;
                        enum isisd;
                        enum nhrpd;
                        enum ospf6d;
                        enum pathd;
                        enum pim6d;
                        enum ripd;
                        enum staticd;
                        enum zebra;
                    }
                }                  //<babeld|bgpd|fabricd|ldpd|ospfd|pbrd|pimd|ripngd|vrrpd|bfdd|eigrpd|isisd|nhrpd|ospf6d|pathd|pim6d|ripd|staticd|zebra> ['For the babeld daemon', 'For the bgpd daemon', 'For the fabricd daemon', 'For the ldpd daemon', 'For the ospfd daemon', 'For the pbrd daemon', 'For the pimd daemon', 'For the ripngd daemon', 'For the vrrpd daemon', 'For the bfdd daemon', 'For the eigrpd daemon', 'For the isisd daemon', 'For the nhrpd daemon', 'For the ospf6d daemon', 'For the pathd daemon', 'For the pim6d daemom', 'For the ripd daemon', 'For the staticd daemon', 'For the zebra daemon']
            }
            container show_mpls {
                leaf pseudowires {
                    type enumeration {
                        enum pseudowires;
                    }
                }                  //pseudowires
                leaf status {
                    type enumeration {
                        enum status;
                    }
                }                  //status
            }
            container show_pbr {
                leaf rule {
                    type enumeration {
                        enum rule;
                    }
                }                  //rule
            }
            container show_rpki {
                leaf as-number {
                    type enumeration {
                        enum as-number;
                    }
                }                  //as-number
                leaf AS_NUMBER {
                    type int32;
                }                  //(1-4294967295)
                leaf json {
                    type enumeration {
                        enum json;
                    }
                }                  //json
                leaf prefix {
                    type enumeration {
                        enum prefix;
                    }
                }                  //prefix
                leaf IPV4_PREFIX {
                    type union {
                        type inet:ipv4-prefix;
                        type inet:ipv6-prefix;
                    }
                }                  //<A.B.C.D/M|X:X::X:X/M>
            }
            container show_running-config {
                leaf DAEMONS_LIST {
                    type enumeration {
                        enum babeld;
                        enum bgpd;
                        enum fabricd;
                        enum ldpd;
                        enum ospfd;
                        enum pbrd;
                        enum pimd;
                        enum ripngd;
                        enum vrrpd;
                        enum bfdd;
                        enum eigrpd;
                        enum isisd;
                        enum nhrpd;
                        enum ospf6d;
                        enum pathd;
                        enum pim6d;
                        enum ripd;
                        enum staticd;
                        enum zebra;
                    }
                }                  //<babeld|bgpd|fabricd|ldpd|ospfd|pbrd|pimd|ripngd|vrrpd|bfdd|eigrpd|isisd|nhrpd|ospf6d|pathd|pim6d|ripd|staticd|zebra> ['For the babeld daemon', 'For the bgpd daemon', 'For the fabricd daemon', 'For the ldpd daemon', 'For the ospfd daemon', 'For the pbrd daemon', 'For the pimd daemon', 'For the ripngd daemon', 'For the vrrpd daemon', 'For the bfdd daemon', 'For the eigrpd daemon', 'For the isisd daemon', 'For the nhrpd daemon', 'For the ospf6d daemon', 'For the pathd daemon', 'For the pim6d daemom', 'For the ripd daemon', 'For the staticd daemon', 'For the zebra daemon']
                leaf no-header {
                    type enumeration {
                        enum no-header;
                    }
                }                  //no-header
            }
            container show_thread {
                leaf poll {
                    type enumeration {
                        enum poll;
                    }
                }                  //poll
                leaf timers {
                    type enumeration {
                        enum timers;
                    }
                }                  //timers
            }
            container show_vnc {
                leaf summary {
                    type enumeration {
                        enum summary;
                    }
                }                  //summary
            }
            container show_vrf {
                leaf THE_VRF_NAME {
                    type string;
                }                  //NAME
                leaf all {
                    type enumeration {
                        enum all;
                    }
                }
                leaf vni {
                    type enumeration {
                        enum vni;
                    }
                }                  //vni
                leaf vni_json {
                    type enumeration {
                        enum vni_json;
                    }
                }                  //json
            }
            container show_vrrp {
                leaf interface {
                    type enumeration {
                        enum interface;
                    }
                }                  //interface
                leaf ONLY_SHOW_VRRP_INSTANCES {
                    type string;
                }                  //INTERFACE
                leaf VIRTUAL_ROUTER_ID {
                    type int32;
                }                  //(1-255)
                leaf json {
                    type enumeration {
                        enum json;
                    }
                }                  //json
                leaf summary {
                    type enumeration {
                        enum summary;
                    }
                }                  //summary
            }
            container show_work-queues {
                leaf DAEMONS_LIST {
                    type enumeration {
                        enum babeld;
                        enum bgpd;
                        enum fabricd;
                        enum ldpd;
                        enum ospfd;
                        enum pbrd;
                        enum pimd;
                        enum ripngd;
                        enum vrrpd;
                        enum bfdd;
                        enum eigrpd;
                        enum isisd;
                        enum nhrpd;
                        enum ospf6d;
                        enum pathd;
                        enum pim6d;
                        enum ripd;
                        enum staticd;
                        enum zebra;
                    }
                }                  //<babeld|bgpd|fabricd|ldpd|ospfd|pbrd|pimd|ripngd|vrrpd|bfdd|eigrpd|isisd|nhrpd|ospf6d|pathd|pim6d|ripd|staticd|zebra> ['For the babeld daemon', 'For the bgpd daemon', 'For the fabricd daemon', 'For the ldpd daemon', 'For the ospfd daemon', 'For the pbrd daemon', 'For the pimd daemon', 'For the ripngd daemon', 'For the vrrpd daemon', 'For the bfdd daemon', 'For the eigrpd daemon', 'For the isisd daemon', 'For the nhrpd daemon', 'For the ospf6d daemon', 'For the pathd daemon', 'For the pim6d daemom', 'For the ripd daemon', 'For the staticd daemon', 'For the zebra daemon']
            }
            container show_zebra {
                leaf mlag {
                    type enumeration {
                        enum mlag;
                    }
                }                  //mlag
            }
            container show_bfd {
                leaf vrf {
                    type enumeration {
                        enum vrf;
                    }
                }                  //vrf
                leaf THE_VRF_NAME {
                    type string;
                }                  //NAME
                leaf peers {
                    type enumeration {
                        enum peers;
                    }
                }                  //peers
                leaf peers_json {
                    type enumeration {
                        enum peers_json;
                    }
                }                  //json
                leaf peer {
                    type enumeration {
                        enum peer;
                    }
                }                  //peer
                leaf IP_ADDRESS {
                    type union {
                        type inet:ipv4-address;
                        type inet:ipv6-address;
                    }
                }                  //<A.B.C.D|X:X::X:X>
                leaf multihop {
                    type enumeration {
                        enum multihop;
                    }
                }                  //multihop
                leaf multihop_json {
                    type enumeration {
                        enum multihop_json;
                    }
                }                  //json
                leaf local-address {
                    type enumeration {
                        enum local-address;
                    }
                }                  //local-address
                leaf json {
                    type enumeration {
                        enum json;
                    }
                }                  //json
                leaf counters {
                    type enumeration {
                        enum counters;
                    }
                }                  //counters
                leaf counters_json {
                    type enumeration {
                        enum counters_json;
                    }
                }                  //json
                leaf interface {
                    type enumeration {
                        enum interface;
                    }
                }                  //interface
                leaf CONFIGURE_LOCAL_INTERFACE_NAME {
                    type string;
                }                  //IFNAME
                leaf multihop_counters {
                    type enumeration {
                        enum multihop_counters;
                    }
                }                  //multihop_counters
                leaf multihop_counters_json {
                    type enumeration {
                        enum multihop_counters_json;
                    }
                }                  //json
                leaf peer_json {
                    type enumeration {
                        enum peer_json;
                    }
                }                  //json
                leaf peers_brief {
                    type enumeration {
                        enum peers_brief;
                    }
                }                  //peers_brief
                leaf peers_brief_json {
                    type enumeration {
                        enum peers_brief_json;
                    }
                }                  //json
                leaf peers_counters {
                    type enumeration {
                        enum peers_counters;
                    }
                }                  //peers_counters
                leaf peers_counters_json {
                    type enumeration {
                        enum peers_counters_json;
                    }
                }                  //json
                leaf peer_counters {
                    type enumeration {
                        enum peer_counters;
                    }
                }                  //peer_counters
                leaf peer_counters_json {
                    type enumeration {
                        enum peer_counters_json;
                    }
                }                  //json
                leaf distributed {
                    type enumeration {
                        enum distributed;
                    }
                }                  //distributed
            }
            container show_route-map {
                leaf ROUTE-MAP_NAME {
                    type string;
                }                  //RMAP_NAME
                leaf prefix-table {
                    type enumeration {
                        enum prefix-table;
                    }
                }                  //prefix-table
                leaf json {
                    type enumeration {
                        enum json;
                    }
                }                  //json
            }
            container show_yang {
                leaf module-translator {
                    type enumeration {
                        enum module-translator;
                    }
                }                  //module-translator
                leaf operational-data {
                    type enumeration {
                        enum operational-data;
                    }
                }                  //operational-data
                leaf XPATH_EXPRESSION_SPECIFYING_THE {
                    type string;
                }                  //XPATH
                leaf format {
                    type enumeration {
                        enum format;
                    }
                }                  //format
                leaf OUTPUT_FORMAT {
                    type enumeration {
                        enum json;
                        enum xml;
                    }
                }                  //<json|xml> ['JavaScript Object Notation', 'Extensible Markup Language']
                leaf DAEMONS_LIST {
                    type enumeration {
                        enum babeld;
                        enum bgpd;
                        enum fabricd;
                        enum ldpd;
                        enum ospfd;
                        enum pbrd;
                        enum pimd;
                        enum ripngd;
                        enum vrrpd;
                        enum bfdd;
                        enum eigrpd;
                        enum isisd;
                        enum nhrpd;
                        enum ospf6d;
                        enum pathd;
                        enum pim6d;
                        enum ripd;
                        enum staticd;
                        enum zebra;
                    }
                }                  //<babeld|bgpd|fabricd|ldpd|ospfd|pbrd|pimd|ripngd|vrrpd|bfdd|eigrpd|isisd|nhrpd|ospf6d|pathd|pim6d|ripd|staticd|zebra> ['For the babeld daemon', 'For the bgpd daemon', 'For the fabricd daemon', 'For the ldpd daemon', 'For the ospfd daemon', 'For the pbrd daemon', 'For the pimd daemon', 'For the ripngd daemon', 'For the vrrpd daemon', 'For the bfdd daemon', 'For the eigrpd daemon', 'For the isisd daemon', 'For the nhrpd daemon', 'For the ospf6d daemon', 'For the pathd daemon', 'For the pim6d daemom', 'For the ripd daemon', 'For the staticd daemon', 'For the zebra daemon']
                leaf translate {
                    type enumeration {
                        enum translate;
                    }
                }                  //translate
                leaf YANG_MODULE_TRANSLATOR {
                    type string;
                }                  //WORD
                leaf with-config {
                    type enumeration {
                        enum with-config;
                    }
                }                  //with-config
            }
            container write_terminal {
                leaf DAEMONS_LIST {
                    type enumeration {
                        enum babeld;
                        enum bgpd;
                        enum fabricd;
                        enum ldpd;
                        enum ospfd;
                        enum pbrd;
                        enum pimd;
                        enum ripngd;
                        enum vrrpd;
                        enum bfdd;
                        enum eigrpd;
                        enum isisd;
                        enum nhrpd;
                        enum ospf6d;
                        enum pathd;
                        enum pim6d;
                        enum ripd;
                        enum staticd;
                        enum zebra;
                    }
                }                  //<babeld|bgpd|fabricd|ldpd|ospfd|pbrd|pimd|ripngd|vrrpd|bfdd|eigrpd|isisd|nhrpd|ospf6d|pathd|pim6d|ripd|staticd|zebra> ['For the babeld daemon', 'For the bgpd daemon', 'For the fabricd daemon', 'For the ldpd daemon', 'For the ospfd daemon', 'For the pbrd daemon', 'For the pimd daemon', 'For the ripngd daemon', 'For the vrrpd daemon', 'For the bfdd daemon', 'For the eigrpd daemon', 'For the isisd daemon', 'For the nhrpd daemon', 'For the ospf6d daemon', 'For the pathd daemon', 'For the pim6d daemom', 'For the ripd daemon', 'For the staticd daemon', 'For the zebra daemon']
                leaf no-header {
                    type enumeration {
                        enum no-header;
                    }
                }                  //no-header
            }
            container debug_bfd {
                leaf distributed {
                    type enumeration {
                        enum distributed;
                    }
                }                  //distributed
                leaf network {
                    type enumeration {
                        enum network;
                    }
                }                  //network
                leaf peer {
                    type enumeration {
                        enum peer;
                    }
                }                  //peer
                leaf zebra {
                    type enumeration {
                        enum zebra;
                    }
                }                  //zebra
            }
            container debug_bgp {
                leaf bfd {
                    type enumeration {
                        enum bfd;
                    }
                }                  //bfd
                leaf conditional-advertisement {
                    type enumeration {
                        enum conditional-advertisement;
                    }
                }                  //conditional-advertisement
                leaf bestpath {
                    type enumeration {
                        enum bestpath;
                    }
                }                  //bestpath
                leaf IPV4_PREFIX {
                    type union {
                        type inet:ipv4-prefix;
                        type inet:ipv6-prefix;
                    }
                }                  //<A.B.C.D/M|X:X::X:X/M>
                leaf flowspec {
                    type enumeration {
                        enum flowspec;
                    }
                }                  //flowspec
                leaf graceful-restart {
                    type enumeration {
                        enum graceful-restart;
                    }
                }                  //graceful-restart
                leaf labelpool {
                    type enumeration {
                        enum labelpool;
                    }
                }                  //labelpool
                leaf nht {
                    type enumeration {
                        enum nht;
                    }
                }                  //nht
                leaf update-groups {
                    type enumeration {
                        enum update-groups;
                    }
                }                  //update-groups
                leaf vnc {
                    type enumeration {
                        enum vnc;
                    }
                }                  //vnc
                leaf RFAPI_DEBUG_OPTIONS {
                    type enumeration {
                        enum rfapi-query;
                        enum import-bi-attach;
                        enum import-del-remote;
                        enum verbose;
                    }
                }                  //<rfapi-query|import-bi-attach|import-del-remote|verbose> ['rfapi query handling', 'import BI atachment', 'import delete remote routes', 'verbose logging']
                leaf vpn {
                    type enumeration {
                        enum vpn;
                    }
                }                  //vpn
                leaf VRF_LEAK_EVENT_LABEL {
                    type enumeration {
                        enum leak-from-vrf;
                        enum leak-to-vrf;
                        enum rmap-event;
                        enum label;
                    }
                }                  //<leak-from-vrf|leak-to-vrf|rmap-event|label> ['leaked from vrf to vpn', 'leaked to vrf from vpn', 'route-map updates', 'labels']
            }
            container debug_mld {
                leaf events {
                    type enumeration {
                        enum events;
                    }
                }                  //events
                leaf packets {
                    type enumeration {
                        enum packets;
                    }
                }                  //packets
            }
            container debug_mroute6 {
                leaf detail {
                    type enumeration {
                        enum detail;
                    }
                }                  //detail
            }
            container debug_northbound {
                leaf notifications {
                    type enumeration {
                        enum notifications;
                    }
                }                  //notifications
                leaf events {
                    type enumeration {
                        enum events;
                    }
                }                  //events
                leaf libyang {
                    type enumeration {
                        enum libyang;
                    }
                }                  //libyang
            }
            container debug_ospf {
                leaf INSTANCE_ID {
                    type int32;
                }                  //(1-65535)
                leaf bfd {
                    type enumeration {
                        enum bfd;
                    }
                }                  //bfd
                leaf client-api {
                    type enumeration {
                        enum client-api;
                    }
                }                  //client-api
                leaf default-information {
                    type enumeration {
                        enum default-information;
                    }
                }                  //default-information
                leaf graceful-restart {
                    type enumeration {
                        enum graceful-restart;
                    }
                }                  //graceful-restart
                leaf ldp-sync {
                    type enumeration {
                        enum ldp-sync;
                    }
                }                  //ldp-sync
                leaf packet {
                    type enumeration {
                        enum packet;
                    }
                }                  //packet
                leaf OSPF_PACKET_TYPE {
                    type enumeration {
                        enum hello;
                        enum dd;
                        enum ls-request;
                        enum ls-update;
                        enum ls-ack;
                        enum all;
                    }
                }                  //<hello|dd|ls-request|ls-update|ls-ack|all> ['OSPF Hello', 'OSPF Database Description', 'OSPF Link State Request', 'OSPF Link State Update', 'OSPF Link State Acknowledgment', 'OSPF all packets']
                leaf send {
                    type enumeration {
                        enum send;
                    }
                }                  //send
                leaf send_detail {
                    type enumeration {
                        enum send_detail;
                    }
                }                  //detail
                leaf recv {
                    type enumeration {
                        enum recv;
                    }
                }                  //recv
                leaf recv_detail {
                    type enumeration {
                        enum recv_detail;
                    }
                }                  //detail
                leaf detail {
                    type enumeration {
                        enum detail;
                    }
                }                  //detail
                leaf sr {
                    type enumeration {
                        enum sr;
                    }
                }                  //sr
                leaf te {
                    type enumeration {
                        enum te;
                    }
                }                  //te
                leaf ti-lfa {
                    type enumeration {
                        enum ti-lfa;
                    }
                }                  //ti-lfa
                leaf event {
                    type enumeration {
                        enum event;
                    }
                }                  //event
                leaf lsa {
                    type enumeration {
                        enum lsa;
                    }
                }                  //lsa
                leaf LSA_OPERATION_TYPE {
                    type enumeration {
                        enum generate;
                        enum flooding;
                        enum install;
                        enum refresh;
                        enum aggregate;
                    }
                }                  //<generate|flooding|install|refresh|aggregate> ['LSA Generation', 'LSA Flooding', 'LSA Install/Delete', 'LSA Refresh', 'External LSA Aggregation']
                leaf nsm {
                    type enumeration {
                        enum nsm;
                    }
                }                  //nsm
                leaf NSM_STATUS_EVENT_TIMER {
                    type enumeration {
                        enum status;
                        enum events;
                        enum timers;
                    }
                }                  //<status|events|timers> ['NSM Status Information', 'NSM Event Information', 'NSM Timer Information']
                leaf nssa {
                    type enumeration {
                        enum nssa;
                    }
                }                  //nssa
                leaf zebra {
                    type enumeration {
                        enum zebra;
                    }
                }                  //zebra
                leaf ZEBRA_INTERFACE_REDISTRIBUTE {
                    type enumeration {
                        enum interface;
                        enum redistribute;
                    }
                }                  //<interface|redistribute> ['Zebra interface', 'Zebra redistribute']
                leaf ism {
                    type enumeration {
                        enum ism;
                    }
                }                  //ism
            }
            container debug_ospf6 {
                leaf abr {
                    type enumeration {
                        enum abr;
                    }
                }                  //abr
                leaf asbr {
                    type enumeration {
                        enum asbr;
                    }
                }                  //asbr
                leaf flooding {
                    type enumeration {
                        enum flooding;
                    }
                }                  //flooding
                leaf interface {
                    type enumeration {
                        enum interface;
                    }
                }                  //interface
                leaf message {
                    type enumeration {
                        enum message;
                    }
                }                  //message
                leaf OSPF_DEBUG_PACKET_TYPE {
                    type enumeration {
                        enum unknown;
                        enum hello;
                        enum dbdesc;
                        enum lsreq;
                        enum lsupdate;
                        enum lsack;
                        enum all;
                    }
                }                  //<unknown|hello|dbdesc|lsreq|lsupdate|lsack|all> ['Debug Unknown message', 'Debug Hello message', 'Debug Database Description message', 'Debug Link State Request message', 'Debug Link State Update message', 'Debug Link State Acknowledgement message', 'Debug All message']
                leaf DEBUG_PACKET_DIRECTION {
                    type enumeration {
                        enum send;
                        enum recv;
                        enum send-hdr;
                        enum recv-hdr;
                    }
                }                  //<send|recv|send-hdr|recv-hdr> ['Debug only sending message, entire packet', 'Debug only receiving message, entire packet', 'Debug only sending message, header only', 'Debug only receiving message, header only']
                leaf nssa {
                    type enumeration {
                        enum nssa;
                    }
                }                  //nssa
            }
            container debug_pbr {
                leaf map {
                    type enumeration {
                        enum map;
                    }
                }                  //map
                leaf zebra {
                    type enumeration {
                        enum zebra;
                    }
                }                  //zebra
                leaf nht {
                    type enumeration {
                        enum nht;
                    }
                }                  //nht
                leaf events {
                    type enumeration {
                        enum events;
                    }
                }                  //events
            }
            container debug_pim {
                leaf events {
                    type enumeration {
                        enum events;
                    }
                }                  //events
                leaf zebra {
                    type enumeration {
                        enum zebra;
                    }
                }                  //zebra
                leaf bsm {
                    type enumeration {
                        enum bsm;
                    }
                }                  //bsm
                leaf mlag {
                    type enumeration {
                        enum mlag;
                    }
                }                  //mlag
                leaf static {
                    type enumeration {
                        enum static;
                    }
                }                  //static
                leaf vxlan {
                    type enumeration {
                        enum vxlan;
                    }
                }                  //vxlan
            }
            container debug_pimv6 {
                leaf bsm {
                    type enumeration {
                        enum bsm;
                    }
                }                  //bsm
                leaf events {
                    type enumeration {
                        enum events;
                    }
                }                  //events
                leaf zebra {
                    type enumeration {
                        enum zebra;
                    }
                }                  //zebra
            }
            container debug_static {
                leaf events {
                    type enumeration {
                        enum events;
                    }
                }                  //events
                leaf route {
                    type enumeration {
                        enum route;
                    }
                }                  //route
                leaf bfd {
                    type enumeration {
                        enum bfd;
                    }
                }                  //bfd
            }
            container debug_vrrp {
                leaf protocol {
                    type enumeration {
                        enum protocol;
                    }
                }                  //protocol
                leaf autoconfigure {
                    type enumeration {
                        enum autoconfigure;
                    }
                }                  //autoconfigure
                leaf packets {
                    type enumeration {
                        enum packets;
                    }
                }                  //packets
                leaf sockets {
                    type enumeration {
                        enum sockets;
                    }
                }                  //sockets
                leaf ndisc {
                    type enumeration {
                        enum ndisc;
                    }
                }                  //ndisc
                leaf arp {
                    type enumeration {
                        enum arp;
                    }
                }                  //arp
                leaf zebra {
                    type enumeration {
                        enum zebra;
                    }
                }                  //zebra
            }
            container debug_zebra {
                leaf mlag {
                    type enumeration {
                        enum mlag;
                    }
                }                  //mlag
                leaf neigh {
                    type enumeration {
                        enum neigh;
                    }
                }                  //neigh
                leaf pseudowires {
                    type enumeration {
                        enum pseudowires;
                    }
                }                  //pseudowires
                leaf events {
                    type enumeration {
                        enum events;
                    }
                }                  //events
                leaf fpm {
                    type enumeration {
                        enum fpm;
                    }
                }                  //fpm
                leaf pbr {
                    type enumeration {
                        enum pbr;
                    }
                }                  //pbr
                leaf tc {
                    type enumeration {
                        enum tc;
                    }
                }                  //tc
                leaf vxlan {
                    type enumeration {
                        enum vxlan;
                    }
                }                  //vxlan
            }
            container debug_eigrp {
                leaf packets {
                    type enumeration {
                        enum packets;
                    }
                }                  //packets
                leaf EIGRP_PACKET_TYPE {
                    type enumeration {
                        enum siaquery;
                        enum siareply;
                        enum ack;
                        enum hello;
                        enum probe;
                        enum query;
                        enum reply;
                        enum request;
                        enum retry;
                        enum stub;
                        enum terse;
                        enum update;
                        enum all;
                    }
                }                  //<siaquery|siareply|ack|hello|probe|query|reply|request|retry|stub|terse|update|all> ['EIGRP packets', 'EIGRP SIA-Query packets', 'EIGRP SIA-Reply packets', 'EIGRP ack packets', 'EIGRP hello packets', 'EIGRP probe packets', 'EIGRP query packets', 'EIGRP reply packets', 'EIGRP request packets', 'EIGRP retransmissions', 'EIGRP stub packets', 'Display all EIGRP packets except Hellos', 'EIGRP update packets']
                leaf send {
                    type enumeration {
                        enum send;
                    }
                }                  //send
                leaf send_detail {
                    type enumeration {
                        enum send_detail;
                    }
                }                  //detail
                leaf receive {
                    type enumeration {
                        enum receive;
                    }
                }                  //receive
                leaf receive_detail {
                    type enumeration {
                        enum receive_detail;
                    }
                }                  //detail
                leaf detail {
                    type enumeration {
                        enum detail;
                    }
                }                  //detail
                leaf transmit {
                    type enumeration {
                        enum transmit;
                    }
                }                  //transmit
                leaf EIGRP_PACKET_EVENT {
                    type enumeration {
                        enum send;
                        enum recv;
                        enum all;
                    }
                }                  //<send|recv|all> ['EIGRP transmission events', 'packet sent', 'packet received']
            }
            container debug_igmp {
                leaf events {
                    type enumeration {
                        enum events;
                    }
                }                  //events
                leaf packets {
                    type enumeration {
                        enum packets;
                    }
                }                  //packets
            }
            container debug_isis {
                leaf adj-packets {
                    type enumeration {
                        enum adj-packets;
                    }
                }                  //adj-packets
                leaf bfd {
                    type enumeration {
                        enum bfd;
                    }
                }                  //bfd
                leaf events {
                    type enumeration {
                        enum events;
                    }
                }                  //events
                leaf flooding {
                    type enumeration {
                        enum flooding;
                    }
                }                  //flooding
                leaf ldp-sync {
                    type enumeration {
                        enum ldp-sync;
                    }
                }                  //ldp-sync
                leaf lfa {
                    type enumeration {
                        enum lfa;
                    }
                }                  //lfa
                leaf lsp-gen {
                    type enumeration {
                        enum lsp-gen;
                    }
                }                  //lsp-gen
                leaf lsp-sched {
                    type enumeration {
                        enum lsp-sched;
                    }
                }                  //lsp-sched
                leaf packet-dump {
                    type enumeration {
                        enum packet-dump;
                    }
                }                  //packet-dump
                leaf route-events {
                    type enumeration {
                        enum route-events;
                    }
                }                  //route-events
                leaf snp-packets {
                    type enumeration {
                        enum snp-packets;
                    }
                }                  //snp-packets
                leaf spf-events {
                    type enumeration {
                        enum spf-events;
                    }
                }                  //spf-events
                leaf sr-events {
                    type enumeration {
                        enum sr-events;
                    }
                }                  //sr-events
                leaf te-events {
                    type enumeration {
                        enum te-events;
                    }
                }                  //te-events
                leaf tx-queue {
                    type enumeration {
                        enum tx-queue;
                    }
                }                  //tx-queue
                leaf update-packets {
                    type enumeration {
                        enum update-packets;
                    }
                }                  //update-packets
            }
            container debug_mroute {
                leaf detail {
                    type enumeration {
                        enum detail;
                    }
                }                  //detail
            }
            container debug_msdp {
                leaf events {
                    type enumeration {
                        enum events;
                    }
                }                  //events
                leaf packets {
                    type enumeration {
                        enum packets;
                    }
                }                  //packets
            }
            container debug_rfapi-dev {
                leaf response-omit-self {
                    type enumeration {
                        enum response-omit-self;
                    }
                }                  //response-omit-self
                leaf RESPONSE_FILTER_TOGGLE {
                    type enumeration {
                        enum on;
                        enum off;
                    }
                }                  //<on|off> ['filter out self from responses', 'leave self in responses']
            }
            container debug_rip {
                leaf events {
                    type enumeration {
                        enum events;
                    }
                }                  //events
                leaf zebra {
                    type enumeration {
                        enum zebra;
                    }
                }                  //zebra
            }
            container debug_ripng {
                leaf events {
                    type enumeration {
                        enum events;
                    }
                }                  //events
                leaf zebra {
                    type enumeration {
                        enum zebra;
                    }
                }                  //zebra
            }
            container add_vnc {
                leaf mac {
                    type enumeration {
                        enum mac;
                    }
                }                  //mac
                leaf MAC_ADDRESS {
                    type string;
                }                  //X:X:X:X:X:X
                leaf virtual-network-identifier {
                    type enumeration {
                        enum virtual-network-identifier;
                    }
                }                  //virtual-network-identifier
                leaf VIRTUAL_NETWORK_IDENTIFIER {
                    type int32;
                }                  //(1-4294967295)
                leaf vn {
                    type enumeration {
                        enum vn;
                    }
                }                  //vn
                leaf IP_ADDRESS {
                    type union {
                        type inet:ipv4-address;
                        type inet:ipv6-address;
                    }
                }                  //<A.B.C.D|X:X::X:X>
                leaf un {
                    type enumeration {
                        enum un;
                    }
                }                  //un
                leaf cost {
                    type enumeration {
                        enum cost;
                    }
                }                  //cost
                leaf COST_VALUE {
                    type int32;
                }                  //(0-255)
                leaf lifetime {
                    type enumeration {
                        enum lifetime;
                    }
                }                  //lifetime
                leaf LIFETIME_VALUE_IN_SECONDS {
                    type int32;
                }                  //(1-4294967295)
                leaf prefix {
                    type enumeration {
                        enum prefix;
                    }
                }                  //prefix
                leaf IPV4_PREFIX {
                    type union {
                        type inet:ipv4-prefix;
                        type inet:ipv6-prefix;
                    }
                }                  //<A.B.C.D/M|X:X::X:X/M>
                leaf-list LOCAL-NEXT-HOP {
                    type string;
                }                  //LNH_OPTIONS...
            }
            container clear_ip {
                leaf nhrp {
                    type enumeration {
                        enum nhrp;
                    }
                }                  //nhrp
                leaf ROUTE_CACHE_MODE {
                    type enumeration {
                        enum cache;
                        enum shortcut;
                    }
                }                  //<cache|shortcut> ['Dynamic cache entries', 'Shortcut entries']
            }
            container clear_ipv6 {
                leaf nhrp {
                    type enumeration {
                        enum nhrp;
                    }
                }                  //nhrp
                leaf ROUTE_CACHE_MODE {
                    type enumeration {
                        enum cache;
                        enum shortcut;
                    }
                }                  //<cache|shortcut> ['Dynamic cache entries', 'Shortcut entries']
            }
            container clear_bgp {
                leaf INSTANCE_VIEW_VRF {
                    type enumeration {
                        enum view;
                        enum vrf;
                    }
                }                  //<view|vrf> ['BGP view', 'BGP VRF']
                leaf VIEWVRF_NAME {
                    type string;
                }                  //VIEWVRFNAME
                leaf ipv6 {
                    type enumeration {
                        enum ipv6;
                    }
                }                  //ipv6
                leaf ADDRESS_FAMILY_MODIFIER {
                    type enumeration {
                        enum unicast;
                        enum multicast;
                        enum vpn;
                    }
                }                  //<unicast|multicast|vpn> ['Address Family modifier', 'Address Family modifier', 'Address Family modifier']
                leaf prefix {
                    type enumeration {
                        enum prefix;
                    }
                }                  //prefix
                leaf IPV6_PREFIX {
                    type inet:ipv6-prefix;
                }                  //X:X::X:X/M
            }
            container clear_bfd {
                leaf vrf {
                    type enumeration {
                        enum vrf;
                    }
                }                  //vrf
                leaf THE_VRF_NAME {
                    type string;
                }                  //NAME
                leaf peer {
                    type enumeration {
                        enum peer;
                    }
                }                  //peer
                leaf PEER_LABEL {
                    type string;
                }                  //WORD
                leaf counters {
                    type enumeration {
                        enum counters;
                    }
                }                  //counters
                leaf IP_ADDRESS {
                    type union {
                        type inet:ipv4-address;
                        type inet:ipv6-address;
                    }
                }                  //<A.B.C.D|X:X::X:X>
                leaf multihop_counters {
                    type enumeration {
                        enum multihop_counters;
                    }
                }                  //counters
                leaf local-address {
                    type enumeration {
                        enum local-address;
                    }
                }                  //local-address
                leaf interface {
                    type enumeration {
                        enum interface;
                    }
                }                  //interface
                leaf CONFIGURE_LOCAL_INTERFACE_NAME {
                    type string;
                }                  //IFNAME
            }
            container clear_fpm {
                leaf counters {
                    type enumeration {
                        enum counters;
                    }
                }                  //counters
            }
            container clear_isis {
                leaf vrf {
                    type enumeration {
                        enum vrf;
                    }
                }                  //vrf
                leaf THE_VRF_NAME {
                    type string;
                }                  //NAME
                leaf all {
                    type enumeration {
                        enum all;
                    }
                }
                leaf neighbor {
                    type enumeration {
                        enum neighbor;
                    }
                }                  //neighbor
            }
            container clear_log {
                leaf cmdline-targets {
                    type enumeration {
                        enum cmdline-targets;
                    }
                }                  //cmdline-targets
            }
            container clear_vnc {
                leaf counters {
                    type enumeration {
                        enum counters;
                    }
                }                  //counters
                leaf mac {
                    type enumeration {
                        enum mac;
                    }
                }                  //mac
                leaf ALL_MACS {
                    type union {
                        type string;
                        type string;
                    }
                }                  //<*|X:X:X:X:X:X>
                leaf virtual-network-identifier {
                    type enumeration {
                        enum virtual-network-identifier;
                    }
                }                  //virtual-network-identifier
                leaf ANY_VIRTUAL_NETWORK_IDENTIFIER {
                    type union {
                        type string;
                        type int32;
                    }
                }                  //<*|(1-4294967295)>
                leaf FROM_ANY_NVE {
                    type string;
                }                  //*
                leaf prefix {
                    type enumeration {
                        enum prefix;
                    }
                }                  //prefix
                leaf IPV4_PREFIX {
                    type union {
                        type string;
                        type inet:ipv4-prefix;
                        type inet:ipv6-prefix;
                    }
                }                  //<*|A.B.C.D/M|X:X::X:X/M>
                leaf un {
                    type enumeration {
                        enum un;
                    }
                }                  //un
                leaf IP_ADDRESS {
                    type union {
                        type string;
                        type inet:ipv4-address;
                        type inet:ipv6-address;
                    }
                }                  //<*|A.B.C.D|X:X::X:X>
                leaf vn {
                    type enumeration {
                        enum vn;
                    }
                }                  //vn
            }
            container copy_running-config {
                leaf startup-config {
                    type enumeration {
                        enum startup-config;
                    }
                }                  //startup-config
            }
            container no_terminal_monitor {
                leaf DAEMONS_LIST {
                    type enumeration {
                        enum babeld;
                        enum bgpd;
                        enum fabricd;
                        enum ldpd;
                        enum ospfd;
                        enum pbrd;
                        enum pimd;
                        enum ripngd;
                        enum vrrpd;
                        enum bfdd;
                        enum eigrpd;
                        enum isisd;
                        enum nhrpd;
                        enum ospf6d;
                        enum pathd;
                        enum pim6d;
                        enum ripd;
                        enum staticd;
                        enum zebra;
                    }
                }                  //<babeld|bgpd|fabricd|ldpd|ospfd|pbrd|pimd|ripngd|vrrpd|bfdd|eigrpd|isisd|nhrpd|ospf6d|pathd|pim6d|ripd|staticd|zebra> ['For the babeld daemon', 'For the bgpd daemon', 'For the fabricd daemon', 'For the ldpd daemon', 'For the ospfd daemon', 'For the pbrd daemon', 'For the pimd daemon', 'For the ripngd daemon', 'For the vrrpd daemon', 'For the bfdd daemon', 'For the eigrpd daemon', 'For the isisd daemon', 'For the nhrpd daemon', 'For the ospf6d daemon', 'For the pathd daemon', 'For the pim6d daemom', 'For the ripd daemon', 'For the staticd daemon', 'For the zebra daemon']
            }
            container no_output_file {
                leaf PATH_TO_DUMP_OUTPUT {
                    type string;
                }                  //FILE
            }
            container no_set_ip {
                leaf next-hop {
                    type enumeration {
                        enum next-hop;
                    }
                }                  //next-hop
                leaf IP_ADDRESS_OF_NEXT {
                    type inet:ipv4-address;
                }                  //A.B.C.D
            }
            container no_debug_bfd {
                leaf distributed {
                    type enumeration {
                        enum distributed;
                    }
                }                  //distributed
                leaf network {
                    type enumeration {
                        enum network;
                    }
                }                  //network
                leaf peer {
                    type enumeration {
                        enum peer;
                    }
                }                  //peer
                leaf zebra {
                    type enumeration {
                        enum zebra;
                    }
                }                  //zebra
            }
            container no_debug_bgp {
                leaf bfd {
                    type enumeration {
                        enum bfd;
                    }
                }                  //bfd
                leaf conditional-advertisement {
                    type enumeration {
                        enum conditional-advertisement;
                    }
                }                  //conditional-advertisement
                leaf flowspec {
                    type enumeration {
                        enum flowspec;
                    }
                }                  //flowspec
                leaf graceful-restart {
                    type enumeration {
                        enum graceful-restart;
                    }
                }                  //graceful-restart
                leaf labelpool {
                    type enumeration {
                        enum labelpool;
                    }
                }                  //labelpool
                leaf nht {
                    type enumeration {
                        enum nht;
                    }
                }                  //nht
                leaf update-groups {
                    type enumeration {
                        enum update-groups;
                    }
                }                  //update-groups
                leaf vnc {
                    type enumeration {
                        enum vnc;
                    }
                }                  //vnc
                leaf RFAPI_DEBUG_OPTIONS {
                    type enumeration {
                        enum rfapi-query;
                        enum import-bi-attach;
                        enum import-del-remote;
                        enum verbose;
                    }
                }                  //<rfapi-query|import-bi-attach|import-del-remote|verbose> ['rfapi query handling', 'import BI atachment', 'import delete remote routes', 'verbose logging']
                leaf vpn {
                    type enumeration {
                        enum vpn;
                    }
                }                  //vpn
                leaf VRF_LEAK_EVENT_LABEL {
                    type enumeration {
                        enum leak-from-vrf;
                        enum leak-to-vrf;
                        enum rmap-event;
                        enum label;
                    }
                }                  //<leak-from-vrf|leak-to-vrf|rmap-event|label> ['leaked from vrf to vpn', 'leaked to vrf from vpn', 'route-map updates', 'labels']
            }
            container no_debug_mld {
                leaf events {
                    type enumeration {
                        enum events;
                    }
                }                  //events
                leaf packets {
                    type enumeration {
                        enum packets;
                    }
                }                  //packets
            }
            container no_debug_mroute6 {
                leaf detail {
                    type enumeration {
                        enum detail;
                    }
                }                  //detail
            }
            container no_debug_northbound {
                leaf notifications {
                    type enumeration {
                        enum notifications;
                    }
                }                  //notifications
                leaf events {
                    type enumeration {
                        enum events;
                    }
                }                  //events
                leaf libyang {
                    type enumeration {
                        enum libyang;
                    }
                }                  //libyang
            }
            container no_debug_ospf {
                leaf INSTANCE_ID {
                    type int32;
                }                  //(1-65535)
                leaf bfd {
                    type enumeration {
                        enum bfd;
                    }
                }                  //bfd
                leaf client-api {
                    type enumeration {
                        enum client-api;
                    }
                }                  //client-api
                leaf default-information {
                    type enumeration {
                        enum default-information;
                    }
                }                  //default-information
                leaf graceful-restart {
                    type enumeration {
                        enum graceful-restart;
                    }
                }                  //graceful-restart
                leaf ldp-sync {
                    type enumeration {
                        enum ldp-sync;
                    }
                }                  //ldp-sync
                leaf packet {
                    type enumeration {
                        enum packet;
                    }
                }                  //packet
                leaf OSPF_PACKET_TYPE {
                    type enumeration {
                        enum hello;
                        enum dd;
                        enum ls-request;
                        enum ls-update;
                        enum ls-ack;
                        enum all;
                    }
                }                  //<hello|dd|ls-request|ls-update|ls-ack|all> ['OSPF Hello', 'OSPF Database Description', 'OSPF Link State Request', 'OSPF Link State Update', 'OSPF Link State Acknowledgment', 'OSPF all packets']
                leaf send {
                    type enumeration {
                        enum send;
                    }
                }                  //send
                leaf send_detail {
                    type enumeration {
                        enum send_detail;
                    }
                }                  //detail
                leaf recv {
                    type enumeration {
                        enum recv;
                    }
                }                  //recv
                leaf recv_detail {
                    type enumeration {
                        enum recv_detail;
                    }
                }                  //detail
                leaf detail {
                    type enumeration {
                        enum detail;
                    }
                }                  //detail
                leaf sr {
                    type enumeration {
                        enum sr;
                    }
                }                  //sr
                leaf te {
                    type enumeration {
                        enum te;
                    }
                }                  //te
                leaf ti-lfa {
                    type enumeration {
                        enum ti-lfa;
                    }
                }                  //ti-lfa
                leaf event {
                    type enumeration {
                        enum event;
                    }
                }                  //event
                leaf lsa {
                    type enumeration {
                        enum lsa;
                    }
                }                  //lsa
                leaf LSA_OPERATION_TYPE {
                    type enumeration {
                        enum generate;
                        enum flooding;
                        enum install;
                        enum refresh;
                        enum aggregate;
                    }
                }                  //<generate|flooding|install|refresh|aggregate> ['LSA Generation', 'LSA Flooding', 'LSA Install/Delete', 'LSA Refres', 'External LSA Aggregation']
                leaf nsm {
                    type enumeration {
                        enum nsm;
                    }
                }                  //nsm
                leaf NSM_STATUS_EVENT_TIMER {
                    type enumeration {
                        enum status;
                        enum events;
                        enum timers;
                    }
                }                  //<status|events|timers> ['NSM Status Information', 'NSM Event Information', 'NSM Timer Information']
                leaf nssa {
                    type enumeration {
                        enum nssa;
                    }
                }                  //nssa
                leaf zebra {
                    type enumeration {
                        enum zebra;
                    }
                }                  //zebra
                leaf ZEBRA_INTERFACE_REDISTRIBUTE {
                    type enumeration {
                        enum interface;
                        enum redistribute;
                    }
                }                  //<interface|redistribute> ['Zebra interface', 'Zebra redistribute']
                leaf ism {
                    type enumeration {
                        enum ism;
                    }
                }                  //ism
            }
            container no_debug_ospf6 {
                leaf abr {
                    type enumeration {
                        enum abr;
                    }
                }                  //abr
                leaf asbr {
                    type enumeration {
                        enum asbr;
                    }
                }                  //asbr
                leaf flooding {
                    type enumeration {
                        enum flooding;
                    }
                }                  //flooding
                leaf interface {
                    type enumeration {
                        enum interface;
                    }
                }                  //interface
                leaf message {
                    type enumeration {
                        enum message;
                    }
                }                  //message
                leaf OSPF_DEBUG_PACKET_TYPE {
                    type enumeration {
                        enum unknown;
                        enum hello;
                        enum dbdesc;
                        enum lsreq;
                        enum lsupdate;
                        enum lsack;
                        enum all;
                    }
                }                  //<unknown|hello|dbdesc|lsreq|lsupdate|lsack|all> ['Debug Unknown message', 'Debug Hello message', 'Debug Database Description message', 'Debug Link State Request message', 'Debug Link State Update message', 'Debug Link State Acknowledgement message', 'Debug All message']
                leaf DEBUG_PACKET_DIRECTION {
                    type enumeration {
                        enum send;
                        enum recv;
                        enum send-hdr;
                        enum recv-hdr;
                    }
                }                  //<send|recv|send-hdr|recv-hdr> ['Debug only sending message, entire pkt', 'Debug only receiving message, entire pkt', 'Debug only sending message, header only', 'Debug only receiving message, header only']
                leaf nssa {
                    type enumeration {
                        enum nssa;
                    }
                }                  //nssa
            }
            container no_debug_pbr {
                leaf map {
                    type enumeration {
                        enum map;
                    }
                }                  //map
                leaf zebra {
                    type enumeration {
                        enum zebra;
                    }
                }                  //zebra
                leaf nht {
                    type enumeration {
                        enum nht;
                    }
                }                  //nht
                leaf events {
                    type enumeration {
                        enum events;
                    }
                }                  //events
            }
            container no_debug_pim {
                leaf events {
                    type enumeration {
                        enum events;
                    }
                }                  //events
                leaf zebra {
                    type enumeration {
                        enum zebra;
                    }
                }                  //zebra
                leaf bsm {
                    type enumeration {
                        enum bsm;
                    }
                }                  //bsm
                leaf mlag {
                    type enumeration {
                        enum mlag;
                    }
                }                  //mlag
                leaf static {
                    type enumeration {
                        enum static;
                    }
                }                  //static
                leaf vxlan {
                    type enumeration {
                        enum vxlan;
                    }
                }                  //vxlan
            }
            container no_debug_pimv6 {
                leaf bsm {
                    type enumeration {
                        enum bsm;
                    }
                }                  //bsm
                leaf events {
                    type enumeration {
                        enum events;
                    }
                }                  //events
                leaf zebra {
                    type enumeration {
                        enum zebra;
                    }
                }                  //zebra
            }
            container no_debug_static {
                leaf events {
                    type enumeration {
                        enum events;
                    }
                }                  //events
                leaf route {
                    type enumeration {
                        enum route;
                    }
                }                  //route
                leaf bfd {
                    type enumeration {
                        enum bfd;
                    }
                }                  //bfd
            }
            container no_debug_vrrp {
                leaf protocol {
                    type enumeration {
                        enum protocol;
                    }
                }                  //protocol
                leaf autoconfigure {
                    type enumeration {
                        enum autoconfigure;
                    }
                }                  //autoconfigure
                leaf packets {
                    type enumeration {
                        enum packets;
                    }
                }                  //packets
                leaf sockets {
                    type enumeration {
                        enum sockets;
                    }
                }                  //sockets
                leaf ndisc {
                    type enumeration {
                        enum ndisc;
                    }
                }                  //ndisc
                leaf arp {
                    type enumeration {
                        enum arp;
                    }
                }                  //arp
                leaf zebra {
                    type enumeration {
                        enum zebra;
                    }
                }                  //zebra
            }
            container no_debug_zebra {
                leaf mlag {
                    type enumeration {
                        enum mlag;
                    }
                }                  //mlag
                leaf neigh {
                    type enumeration {
                        enum neigh;
                    }
                }                  //neigh
                leaf pseudowires {
                    type enumeration {
                        enum pseudowires;
                    }
                }                  //pseudowires
                leaf events {
                    type enumeration {
                        enum events;
                    }
                }                  //events
                leaf fpm {
                    type enumeration {
                        enum fpm;
                    }
                }                  //fpm
                leaf pbr {
                    type enumeration {
                        enum pbr;
                    }
                }                  //pbr
                leaf vxlan {
                    type enumeration {
                        enum vxlan;
                    }
                }                  //vxlan
            }
            container no_debug_eigrp {
                leaf packets {
                    type enumeration {
                        enum packets;
                    }
                }                  //packets
                leaf EIGRP_PACKET_TYPE {
                    type enumeration {
                        enum siaquery;
                        enum siareply;
                        enum ack;
                        enum hello;
                        enum probe;
                        enum query;
                        enum reply;
                        enum request;
                        enum retry;
                        enum stub;
                        enum terse;
                        enum update;
                        enum all;
                    }
                }                  //<siaquery|siareply|ack|hello|probe|query|reply|request|retry|stub|terse|update|all> ['EIGRP packets', 'EIGRP SIA-Query packets', 'EIGRP SIA-Reply packets', 'EIGRP ack packets', 'EIGRP hello packets', 'EIGRP probe packets', 'EIGRP query packets', 'EIGRP reply packets', 'EIGRP request packets', 'EIGRP retransmissions', 'EIGRP stub packets', 'Display all EIGRP packets except Hellos', 'EIGRP update packets']
                leaf send {
                    type enumeration {
                        enum send;
                    }
                }                  //send
                leaf send_detail {
                    type enumeration {
                        enum send_detail;
                    }
                }                  //detail
                leaf receive {
                    type enumeration {
                        enum receive;
                    }
                }                  //receive
                leaf receive_detail {
                    type enumeration {
                        enum receive_detail;
                    }
                }                  //detail
                leaf detail {
                    type enumeration {
                        enum detail;
                    }
                }                  //detail
                leaf transmit {
                    type enumeration {
                        enum transmit;
                    }
                }                  //transmit
                leaf EIGRP_PACKET_EVENT {
                    type enumeration {
                        enum send;
                        enum recv;
                        enum all;
                    }
                }                  //<send|recv|all> ['EIGRP transmission events', 'packet sent', 'packet received']
            }
            container no_debug_igmp {
                leaf events {
                    type enumeration {
                        enum events;
                    }
                }                  //events
                leaf packets {
                    type enumeration {
                        enum packets;
                    }
                }                  //packets
            }
            container no_debug_isis {
                leaf adj-packets {
                    type enumeration {
                        enum adj-packets;
                    }
                }                  //adj-packets
                leaf bfd {
                    type enumeration {
                        enum bfd;
                    }
                }                  //bfd
                leaf events {
                    type enumeration {
                        enum events;
                    }
                }                  //events
                leaf flooding {
                    type enumeration {
                        enum flooding;
                    }
                }                  //flooding
                leaf ldp-sync {
                    type enumeration {
                        enum ldp-sync;
                    }
                }                  //ldp-sync
                leaf lfa {
                    type enumeration {
                        enum lfa;
                    }
                }                  //lfa
                leaf lsp-gen {
                    type enumeration {
                        enum lsp-gen;
                    }
                }                  //lsp-gen
                leaf lsp-sched {
                    type enumeration {
                        enum lsp-sched;
                    }
                }                  //lsp-sched
                leaf packet-dump {
                    type enumeration {
                        enum packet-dump;
                    }
                }                  //packet-dump
                leaf route-events {
                    type enumeration {
                        enum route-events;
                    }
                }                  //route-events
                leaf snp-packets {
                    type enumeration {
                        enum snp-packets;
                    }
                }                  //snp-packets
                leaf spf-events {
                    type enumeration {
                        enum spf-events;
                    }
                }                  //spf-events
                leaf sr-events {
                    type enumeration {
                        enum sr-events;
                    }
                }                  //sr-events
                leaf te-events {
                    type enumeration {
                        enum te-events;
                    }
                }                  //te-events
                leaf tx-queue {
                    type enumeration {
                        enum tx-queue;
                    }
                }                  //tx-queue
                leaf update-packets {
                    type enumeration {
                        enum update-packets;
                    }
                }                  //update-packets
            }
            container no_debug_mroute {
                leaf detail {
                    type enumeration {
                        enum detail;
                    }
                }                  //detail
            }
            container no_debug_msdp {
                leaf events {
                    type enumeration {
                        enum events;
                    }
                }                  //events
                leaf packets {
                    type enumeration {
                        enum packets;
                    }
                }                  //packets
            }
            container no_debug_rip {
                leaf events {
                    type enumeration {
                        enum events;
                    }
                }                  //events
                leaf zebra {
                    type enumeration {
                        enum zebra;
                    }
                }                  //zebra
            }
            container no_debug_ripng {
                leaf events {
                    type enumeration {
                        enum events;
                    }
                }                  //events
                leaf zebra {
                    type enumeration {
                        enum zebra;
                    }
                }                  //zebra
            }
            container show_ip_nhrp {
                leaf json {
                    type enumeration {
                        enum json;
                    }
                }                  //json
            }
            container show_ip_route {
                leaf vrf {
                    type enumeration {
                        enum vrf;
                    }
                }                  //vrf
                leaf THE_VRF_NAME {
                    type string;
                }                  //NAME
                leaf all {
                    type enumeration {
                        enum all;
                    }
                }
                leaf summary {
                    type enumeration {
                        enum summary;
                    }
                }                  //summary
                leaf summary_table {
                    type enumeration {
                        enum summary_table;
                    }
                }                  //table
                leaf THE_TABLE_NUMBER {
                    type int32;
                }                  //(1-4294967295)
                leaf prefix {
                    type enumeration {
                        enum prefix;
                    }
                }                  //prefix
                leaf prefix_json {
                    type enumeration {
                        enum prefix_json;
                    }
                }                  //json
                leaf json {
                    type enumeration {
                        enum json;
                    }
                }                  //json
                leaf summary_json {
                    type enumeration {
                        enum summary_json;
                    }
                }                  //json
                leaf summary_prefix {
                    type enumeration {
                        enum summary_prefix;
                    }
                }                  //summary_prefix
                leaf summary_prefix_json {
                    type enumeration {
                        enum summary_prefix_json;
                    }
                }                  //json
            }
            container show_ip_bgp {
                leaf INSTANCE_VIEW_VRF {
                    type enumeration {
                        enum view;
                        enum vrf;
                    }
                }                  //<view|vrf> ['BGP view', 'BGP VRF']
                leaf VIEWVRF_NAME {
                    type string;
                }                  //VIEWVRFNAME
                leaf update-groups {
                    type enumeration {
                        enum update-groups;
                    }
                }                  //update-groups
                leaf update-groups_statistics {
                    type enumeration {
                        enum update-groups_statistics;
                    }
                }                  //statistics
                leaf ROUTING_QUEUE {
                    type enumeration {
                        enum advertise-queue;
                        enum advertised-routes;
                        enum packet-queue;
                    }
                }                  //<advertise-queue|advertised-routes|packet-queue> ['Advertisement queue', 'Announced routes', 'Packet queue']
                leaf update-groups_json {
                    type enumeration {
                        enum update-groups_json;
                    }
                }                  //json
                leaf REDISTRIBUTE_IP {
                    type enumeration {
                        enum ipv4;
                        enum ipv6;
                    }
                }                  //<ipv4|ipv6> ['Address Family', 'Address Family']
                leaf route-leak {
                    type enumeration {
                        enum route-leak;
                    }
                }                  //route-leak
                leaf route-leak_json {
                    type enumeration {
                        enum route-leak_json;
                    }
                }                  //json
                leaf all {
                    type enumeration {
                        enum all;
                    }
                }                  //all
                leaf all_community-list {
                    type enumeration {
                        enum all_community-list;
                    }
                }                  //community-list
                leaf COMMUNITY-LIST_NAME {
                    type union {
                        type int32;
                        type string;
                    }
                }                  //<(1-500)|COMMUNITY_LIST_NAME>
                leaf exact-match {
                    type enumeration {
                        enum exact-match;
                    }
                }                  //exact-match
                leaf exact-match_wide {
                    type enumeration {
                        enum exact-match_wide;
                    }
                }                  //wide
                leaf json {
                    type enumeration {
                        enum json;
                    }
                }                  //json
                leaf json_detail {
                    type enumeration {
                        enum json_detail;
                    }
                }                  //detail
                leaf wide {
                    type enumeration {
                        enum wide;
                    }
                }                  //wide
                leaf exact-match_json {
                    type enumeration {
                        enum exact-match_json;
                    }
                }                  //exact-match_json
                leaf exact-match_json_detail {
                    type enumeration {
                        enum exact-match_json_detail;
                    }
                }                  //detail
                leaf all_filter-list {
                    type enumeration {
                        enum all_filter-list;
                    }
                }                  //filter-list
                leaf REGULAR_EXPRESSION_ACCESS_LIST {
                    type string;
                }                  //AS_PATH_FILTER_NAME
                leaf all_prefix-list {
                    type enumeration {
                        enum all_prefix-list;
                    }
                }                  //prefix-list
                leaf PREFIX-LIST_NAME {
                    type string;
                }                  //WORD
                leaf all_access-list {
                    type enumeration {
                        enum all_access-list;
                    }
                }                  //access-list
                leaf ACCESS-LIST_NAME {
                    type string;
                }                  //ACCESSLIST_NAME
                leaf all_route-map {
                    type enumeration {
                        enum all_route-map;
                    }
                }                  //route-map
                leaf A_ROUTE-MAP_TO_MATCH {
                    type string;
                }                  //RMAP_NAME
                leaf all_rpki {
                    type enumeration {
                        enum all_rpki;
                    }
                }                  //rpki
                leaf CHOICE_CASE {
                    type enumeration {
                        enum invalid;
                        enum valid;
                        enum notfound;
                    }
                }                  //<invalid|valid|notfound> ['A valid path as determined by rpki', 'A invalid path as determined by rpki', 'A path that has no rpki data']
                leaf all_version {
                    type enumeration {
                        enum all_version;
                    }
                }                  //version
                leaf VERSION_NUMBER_AND_ABOVE {
                    type int32;
                }                  //(1-4294967295)
                leaf all_alias {
                    type enumeration {
                        enum all_alias;
                    }
                }                  //alias
                leaf BGP_COMMUNITY_ALIAS {
                    type string;
                }                  //ALIAS_NAME
                leaf all_wide {
                    type enumeration {
                        enum all_wide;
                    }
                }                  //wide
                leaf all_neighbors {
                    type enumeration {
                        enum all_neighbors;
                    }
                }                  //neighbors
                leaf IP_ADDRESS {
                    type union {
                        type inet:ipv4-address;
                        type inet:ipv6-address;
                        type string;
                    }
                }                  //<A.B.C.D|X:X::X:X|WORD>
                leaf BGP_NEIGHBOR_ROUTE_DIRECTION {
                    type enumeration {
                        enum advertised-routes;
                        enum received-routes;
                        enum filtered-routes;
                    }
                }                  //<advertised-routes|received-routes|filtered-routes> ['Display the routes advertised to a BGP neighbor', 'Display the received routes from neighbor', 'Display the filtered routes received from neighbor']
                leaf route-map {
                    type enumeration {
                        enum route-map;
                    }
                }                  //route-map
                leaf NAME_OF_THE_ROUTE {
                    type string;
                }                  //RMAP_NAME
                leaf detail {
                    type enumeration {
                        enum detail;
                    }
                }                  //detail
                leaf detail_json {
                    type enumeration {
                        enum detail_json;
                    }
                }                  //json
                leaf detail_wide {
                    type enumeration {
                        enum detail_wide;
                    }
                }                  //wide
                leaf cidr-only {
                    type enumeration {
                        enum cidr-only;
                    }
                }                  //cidr-only
                leaf cidr-only_wide {
                    type enumeration {
                        enum cidr-only_wide;
                    }
                }                  //wide
                leaf dampening {
                    type enumeration {
                        enum dampening;
                    }
                }                  //dampening
                leaf community {
                    type enumeration {
                        enum community;
                    }
                }                  //community
                leaf community_wide {
                    type enumeration {
                        enum community_wide;
                    }
                }                  //wide
                leaf community-list {
                    type enumeration {
                        enum community-list;
                    }
                }                  //community-list
                leaf filter-list {
                    type enumeration {
                        enum filter-list;
                    }
                }                  //filter-list
                leaf prefix-list {
                    type enumeration {
                        enum prefix-list;
                    }
                }                  //prefix-list
                leaf access-list {
                    type enumeration {
                        enum access-list;
                    }
                }                  //access-list
                leaf rpki {
                    type enumeration {
                        enum rpki;
                    }
                }                  //rpki
                leaf version {
                    type enumeration {
                        enum version;
                    }
                }                  //version
                leaf alias {
                    type enumeration {
                        enum alias;
                    }
                }                  //alias
                leaf IPV4_PREFIX {
                    type inet:ipv4-prefix;
                }                  //A.B.C.D/M
                leaf longer-prefixes {
                    type enumeration {
                        enum longer-prefixes;
                    }
                }                  //longer-prefixes
                leaf longer-prefixes_wide {
                    type enumeration {
                        enum longer-prefixes_wide;
                    }
                }                  //wide
                leaf longer-prefixes_json {
                    type enumeration {
                        enum longer-prefixes_json;
                    }
                }                  //longer-prefixes_json
                leaf longer-prefixes_json_detail {
                    type enumeration {
                        enum longer-prefixes_json_detail;
                    }
                }                  //detail
                leaf IPV6_PREFIX {
                    type inet:ipv6-prefix;
                }                  //X:X::X:X/M
                leaf detail-routes {
                    type enumeration {
                        enum detail-routes;
                    }
                }                  //detail-routes
                leaf detail-routes_wide {
                    type enumeration {
                        enum detail-routes_wide;
                    }
                }                  //wide
                leaf neighbors {
                    type enumeration {
                        enum neighbors;
                    }
                }                  //neighbors
                leaf BGP_NEIGHBOR_ROUTE_STATS {
                    type enumeration {
                        enum flap-statistics;
                        enum dampened-routes;
                        enum routes;
                    }
                }                  //<flap-statistics|dampened-routes|routes> ['Display flap statistics of the routes learned from neighbor', 'Display the dampened routes received from neighbor', 'Display routes learned from neighbor']
                leaf bestpath-routes {
                    type enumeration {
                        enum bestpath-routes;
                    }
                }                  //bestpath-routes
                leaf bestpath-routes_json {
                    type enumeration {
                        enum bestpath-routes_json;
                    }
                }                  //json
                leaf bestpath-routes_wide {
                    type enumeration {
                        enum bestpath-routes_wide;
                    }
                }                  //wide
                leaf prefix-counts {
                    type enumeration {
                        enum prefix-counts;
                    }
                }                  //prefix-counts
                leaf prefix-counts_json {
                    type enumeration {
                        enum prefix-counts_json;
                    }
                }                  //json
                leaf received_prefix-filter {
                    type enumeration {
                        enum received_prefix-filter;
                    }
                }                  //received_prefix-filter
                leaf received_prefix-filter_json {
                    type enumeration {
                        enum received_prefix-filter_json;
                    }
                }                  //json
                leaf neighbors_json {
                    type enumeration {
                        enum neighbors_json;
                    }
                }                  //json
                leaf summary {
                    type enumeration {
                        enum summary;
                    }
                }                  //summary
                leaf summary_neighbor {
                    type enumeration {
                        enum summary_neighbor;
                    }
                }                  //neighbor
                leaf terse {
                    type enumeration {
                        enum terse;
                    }
                }                  //terse
                leaf terse_json {
                    type enumeration {
                        enum terse_json;
                    }
                }                  //json
                leaf wide_json {
                    type enumeration {
                        enum wide_json;
                    }
                }                  //json
                leaf terse_wide {
                    type enumeration {
                        enum terse_wide;
                    }
                }                  //terse_wide
                leaf terse_wide_json {
                    type enumeration {
                        enum terse_wide_json;
                    }
                }                  //json
                leaf summary_remote-as {
                    type enumeration {
                        enum summary_remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
                leaf summary_json {
                    type enumeration {
                        enum summary_json;
                    }
                }                  //json
                leaf large-community {
                    type enumeration {
                        enum large-community;
                    }
                }                  //large-community
                leaf LARGE_COMMUNITY {
                    type string;
                }                  //AA:BB:CC
                leaf large-community_json {
                    type enumeration {
                        enum large-community_json;
                    }
                }                  //json
                leaf large-community-list {
                    type enumeration {
                        enum large-community-list;
                    }
                }                  //large-community-list
                leaf LARGE-COMMUNITY-LIST_NUMBER {
                    type union {
                        type int32;
                        type string;
                    }
                }                  //<(1-500)|LCOMMUNITY_LIST_NAME>
                leaf regexp {
                    type enumeration {
                        enum regexp;
                    }
                }                  //regexp
                leaf REGULAR_EXPRESSION {
                    type string;
                }                  //REGEX
                leaf statistics {
                    type enumeration {
                        enum statistics;
                    }
                }                  //statistics
                leaf statistics_json {
                    type enumeration {
                        enum statistics_json;
                    }
                }                  //json
                leaf BGP_PATH_SELECTION {
                    type enumeration {
                        enum bestpath;
                        enum multipath;
                    }
                }                  //<bestpath|multipath> ['Display only the bestpath', 'Display only multipaths']
                leaf RPKI_VALIDATION_STATE {
                    type enumeration {
                        enum valid;
                        enum invalid;
                        enum notfound;
                    }
                }                  //<valid|invalid|notfound> ['A valid path as determined by rpki', 'A invalid path as determined by rpki', 'A path that has no rpki data']
                leaf unicast_neighbors {
                    type enumeration {
                        enum unicast_neighbors;
                    }
                }                  //neighbors
                leaf flowspec {
                    type enumeration {
                        enum flowspec;
                    }
                }                  //flowspec
                leaf flowspec_community-list {
                    type enumeration {
                        enum flowspec_community-list;
                    }
                }                  //community-list
                leaf flowspec_filter-list {
                    type enumeration {
                        enum flowspec_filter-list;
                    }
                }                  //filter-list
                leaf flowspec_prefix-list {
                    type enumeration {
                        enum flowspec_prefix-list;
                    }
                }                  //prefix-list
                leaf flowspec_access-list {
                    type enumeration {
                        enum flowspec_access-list;
                    }
                }                  //access-list
                leaf flowspec_route-map {
                    type enumeration {
                        enum flowspec_route-map;
                    }
                }                  //route-map
                leaf flowspec_rpki {
                    type enumeration {
                        enum flowspec_rpki;
                    }
                }                  //rpki
                leaf flowspec_version {
                    type enumeration {
                        enum flowspec_version;
                    }
                }                  //version
                leaf flowspec_alias {
                    type enumeration {
                        enum flowspec_alias;
                    }
                }                  //alias
                leaf flowspec_wide {
                    type enumeration {
                        enum flowspec_wide;
                    }
                }                  //wide
                leaf flowspec_neighbors {
                    type enumeration {
                        enum flowspec_neighbors;
                    }
                }                  //neighbors
                leaf flowspec_large-community-list {
                    type enumeration {
                        enum flowspec_large-community-list;
                    }
                }                  //large-community-list
                leaf flowspec_regexp {
                    type enumeration {
                        enum flowspec_regexp;
                    }
                }                  //regexp
                leaf all_cidr-only {
                    type enumeration {
                        enum all_cidr-only;
                    }
                }                  //all_cidr-only
                leaf all_cidr-only_wide {
                    type enumeration {
                        enum all_cidr-only_wide;
                    }
                }                  //wide
                leaf all_dampening {
                    type enumeration {
                        enum all_dampening;
                    }
                }                  //all_dampening
                leaf all_community {
                    type enumeration {
                        enum all_community;
                    }
                }                  //all_community
                leaf all_community_wide {
                    type enumeration {
                        enum all_community_wide;
                    }
                }                  //wide
                leaf all_detail-routes {
                    type enumeration {
                        enum all_detail-routes;
                    }
                }                  //all_detail-routes
                leaf all_detail-routes_wide {
                    type enumeration {
                        enum all_detail-routes_wide;
                    }
                }                  //wide
                leaf all_json {
                    type enumeration {
                        enum all_json;
                    }
                }                  //all_json
                leaf all_json_detail {
                    type enumeration {
                        enum all_json_detail;
                    }
                }                  //detail
                leaf all_summary {
                    type enumeration {
                        enum all_summary;
                    }
                }                  //all_summary
                leaf all_summary_neighbor {
                    type enumeration {
                        enum all_summary_neighbor;
                    }
                }                  //neighbor
                leaf all_summary_remote-as {
                    type enumeration {
                        enum all_summary_remote-as;
                    }
                }                  //remote-as
                leaf all_summary_json {
                    type enumeration {
                        enum all_summary_json;
                    }
                }                  //json
                leaf cidr-only_json {
                    type enumeration {
                        enum cidr-only_json;
                    }
                }                  //cidr-only_json
                leaf cidr-only_json_detail {
                    type enumeration {
                        enum cidr-only_json_detail;
                    }
                }                  //detail
                leaf dampening_parameters {
                    type enumeration {
                        enum dampening_parameters;
                    }
                }                  //dampening_parameters
                leaf dampening_parameters_json {
                    type enumeration {
                        enum dampening_parameters_json;
                    }
                }                  //json
                leaf community_local-AS {
                    type enumeration {
                        enum community_local-AS;
                    }
                }                  //community_local-AS
                leaf community_local-AS_wide {
                    type enumeration {
                        enum community_local-AS_wide;
                    }
                }                  //wide
                leaf community_no-advertise {
                    type enumeration {
                        enum community_no-advertise;
                    }
                }                  //community_no-advertise
                leaf community_no-advertise_wide {
                    type enumeration {
                        enum community_no-advertise_wide;
                    }
                }                  //wide
                leaf community_no-export {
                    type enumeration {
                        enum community_no-export;
                    }
                }                  //community_no-export
                leaf community_no-export_wide {
                    type enumeration {
                        enum community_no-export_wide;
                    }
                }                  //wide
                leaf community_graceful-shutdown {
                    type enumeration {
                        enum community_graceful-shutdown;
                    }
                }                  //community_graceful-shutdown
                leaf community_graceful-shutdown_wide {
                    type enumeration {
                        enum community_graceful-shutdown_wide;
                    }
                }                  //wide
                leaf community_no-peer {
                    type enumeration {
                        enum community_no-peer;
                    }
                }                  //community_no-peer
                leaf community_no-peer_wide {
                    type enumeration {
                        enum community_no-peer_wide;
                    }
                }                  //wide
                leaf community_blackhole {
                    type enumeration {
                        enum community_blackhole;
                    }
                }                  //community_blackhole
                leaf community_blackhole_wide {
                    type enumeration {
                        enum community_blackhole_wide;
                    }
                }                  //wide
                leaf community_llgr-stale {
                    type enumeration {
                        enum community_llgr-stale;
                    }
                }                  //community_llgr-stale
                leaf community_llgr-stale_wide {
                    type enumeration {
                        enum community_llgr-stale_wide;
                    }
                }                  //wide
                leaf community_no-llgr {
                    type enumeration {
                        enum community_no-llgr;
                    }
                }                  //community_no-llgr
                leaf community_no-llgr_wide {
                    type enumeration {
                        enum community_no-llgr_wide;
                    }
                }                  //wide
                leaf community_accept-own {
                    type enumeration {
                        enum community_accept-own;
                    }
                }                  //community_accept-own
                leaf community_accept-own_wide {
                    type enumeration {
                        enum community_accept-own_wide;
                    }
                }                  //wide
                leaf community_accept-own-nexthop {
                    type enumeration {
                        enum community_accept-own-nexthop;
                    }
                }                  //community_accept-own-nexthop
                leaf community_accept-own-nexthop_wide {
                    type enumeration {
                        enum community_accept-own-nexthop_wide;
                    }
                }                  //wide
                leaf community_route-filter-v6 {
                    type enumeration {
                        enum community_route-filter-v6;
                    }
                }                  //community_route-filter-v6
                leaf community_route-filter-v6_wide {
                    type enumeration {
                        enum community_route-filter-v6_wide;
                    }
                }                  //wide
                leaf community_route-filter-v4 {
                    type enumeration {
                        enum community_route-filter-v4;
                    }
                }                  //community_route-filter-v4
                leaf community_route-filter-v4_wide {
                    type enumeration {
                        enum community_route-filter-v4_wide;
                    }
                }                  //wide
                leaf community_route-filter-translated-v6 {
                    type enumeration {
                        enum community_route-filter-translated-v6;
                    }
                }                  //community_route-filter-translated-v6
                leaf community_route-filter-translated-v6_wide {
                    type enumeration {
                        enum community_route-filter-translated-v6_wide;
                    }
                }                  //wide
                leaf community_route-filter-translated-v4 {
                    type enumeration {
                        enum community_route-filter-translated-v4;
                    }
                }                  //community_route-filter-translated-v4
                leaf community_route-filter-translated-v4_wide {
                    type enumeration {
                        enum community_route-filter-translated-v4_wide;
                    }
                }                  //wide
                leaf community_exact-match {
                    type enumeration {
                        enum community_exact-match;
                    }
                }                  //community_exact-match
                leaf community_exact-match_wide {
                    type enumeration {
                        enum community_exact-match_wide;
                    }
                }                  //wide
                leaf community_json {
                    type enumeration {
                        enum community_json;
                    }
                }                  //community_json
                leaf community_json_detail {
                    type enumeration {
                        enum community_json_detail;
                    }
                }                  //detail
                leaf detail-routes_json {
                    type enumeration {
                        enum detail-routes_json;
                    }
                }                  //detail-routes_json
                leaf detail-routes_json_detail {
                    type enumeration {
                        enum detail-routes_json_detail;
                    }
                }                  //detail
                leaf summary_established {
                    type enumeration {
                        enum summary_established;
                    }
                }                  //summary_established
                leaf summary_established_neighbor {
                    type enumeration {
                        enum summary_established_neighbor;
                    }
                }                  //neighbor
                leaf summary_established_remote-as {
                    type enumeration {
                        enum summary_established_remote-as;
                    }
                }                  //remote-as
                leaf summary_established_json {
                    type enumeration {
                        enum summary_established_json;
                    }
                }                  //json
                leaf summary_failed {
                    type enumeration {
                        enum summary_failed;
                    }
                }                  //summary_failed
                leaf summary_failed_neighbor {
                    type enumeration {
                        enum summary_failed_neighbor;
                    }
                }                  //neighbor
                leaf summary_failed_remote-as {
                    type enumeration {
                        enum summary_failed_remote-as;
                    }
                }                  //remote-as
                leaf summary_failed_json {
                    type enumeration {
                        enum summary_failed_json;
                    }
                }                  //json
                leaf summary_terse {
                    type enumeration {
                        enum summary_terse;
                    }
                }                  //summary_terse
                leaf summary_terse_json {
                    type enumeration {
                        enum summary_terse_json;
                    }
                }                  //json
                leaf summary_wide {
                    type enumeration {
                        enum summary_wide;
                    }
                }                  //summary_wide
                leaf summary_wide_json {
                    type enumeration {
                        enum summary_wide_json;
                    }
                }                  //json
                leaf all_cidr-only_json {
                    type enumeration {
                        enum all_cidr-only_json;
                    }
                }                  //all_cidr-only_json
                leaf all_cidr-only_json_detail {
                    type enumeration {
                        enum all_cidr-only_json_detail;
                    }
                }                  //detail
                leaf all_dampening_parameters {
                    type enumeration {
                        enum all_dampening_parameters;
                    }
                }                  //all_dampening_parameters
                leaf all_dampening_parameters_json {
                    type enumeration {
                        enum all_dampening_parameters_json;
                    }
                }                  //json
                leaf all_community_local-AS {
                    type enumeration {
                        enum all_community_local-AS;
                    }
                }                  //all_community_local-AS
                leaf all_community_local-AS_wide {
                    type enumeration {
                        enum all_community_local-AS_wide;
                    }
                }                  //wide
                leaf all_community_no-advertise {
                    type enumeration {
                        enum all_community_no-advertise;
                    }
                }                  //all_community_no-advertise
                leaf all_community_no-advertise_wide {
                    type enumeration {
                        enum all_community_no-advertise_wide;
                    }
                }                  //wide
                leaf all_community_no-export {
                    type enumeration {
                        enum all_community_no-export;
                    }
                }                  //all_community_no-export
                leaf all_community_no-export_wide {
                    type enumeration {
                        enum all_community_no-export_wide;
                    }
                }                  //wide
                leaf all_community_graceful-shutdown {
                    type enumeration {
                        enum all_community_graceful-shutdown;
                    }
                }                  //all_community_graceful-shutdown
                leaf all_community_graceful-shutdown_wide {
                    type enumeration {
                        enum all_community_graceful-shutdown_wide;
                    }
                }                  //wide
                leaf all_community_no-peer {
                    type enumeration {
                        enum all_community_no-peer;
                    }
                }                  //all_community_no-peer
                leaf all_community_no-peer_wide {
                    type enumeration {
                        enum all_community_no-peer_wide;
                    }
                }                  //wide
                leaf all_community_blackhole {
                    type enumeration {
                        enum all_community_blackhole;
                    }
                }                  //all_community_blackhole
                leaf all_community_blackhole_wide {
                    type enumeration {
                        enum all_community_blackhole_wide;
                    }
                }                  //wide
                leaf all_community_llgr-stale {
                    type enumeration {
                        enum all_community_llgr-stale;
                    }
                }                  //all_community_llgr-stale
                leaf all_community_llgr-stale_wide {
                    type enumeration {
                        enum all_community_llgr-stale_wide;
                    }
                }                  //wide
                leaf all_community_no-llgr {
                    type enumeration {
                        enum all_community_no-llgr;
                    }
                }                  //all_community_no-llgr
                leaf all_community_no-llgr_wide {
                    type enumeration {
                        enum all_community_no-llgr_wide;
                    }
                }                  //wide
                leaf all_community_accept-own {
                    type enumeration {
                        enum all_community_accept-own;
                    }
                }                  //all_community_accept-own
                leaf all_community_accept-own_wide {
                    type enumeration {
                        enum all_community_accept-own_wide;
                    }
                }                  //wide
                leaf all_community_accept-own-nexthop {
                    type enumeration {
                        enum all_community_accept-own-nexthop;
                    }
                }                  //all_community_accept-own-nexthop
                leaf all_community_accept-own-nexthop_wide {
                    type enumeration {
                        enum all_community_accept-own-nexthop_wide;
                    }
                }                  //wide
                leaf all_community_route-filter-v6 {
                    type enumeration {
                        enum all_community_route-filter-v6;
                    }
                }                  //all_community_route-filter-v6
                leaf all_community_route-filter-v6_wide {
                    type enumeration {
                        enum all_community_route-filter-v6_wide;
                    }
                }                  //wide
                leaf all_community_route-filter-v4 {
                    type enumeration {
                        enum all_community_route-filter-v4;
                    }
                }                  //all_community_route-filter-v4
                leaf all_community_route-filter-v4_wide {
                    type enumeration {
                        enum all_community_route-filter-v4_wide;
                    }
                }                  //wide
                leaf all_community_route-filter-translated-v6 {
                    type enumeration {
                        enum all_community_route-filter-translated-v6;
                    }
                }                  //all_community_route-filter-translated-v6
                leaf all_community_route-filter-translated-v6_wide {
                    type enumeration {
                        enum all_community_route-filter-translated-v6_wide;
                    }
                }                  //wide
                leaf all_community_route-filter-translated-v4 {
                    type enumeration {
                        enum all_community_route-filter-translated-v4;
                    }
                }                  //all_community_route-filter-translated-v4
                leaf all_community_route-filter-translated-v4_wide {
                    type enumeration {
                        enum all_community_route-filter-translated-v4_wide;
                    }
                }                  //wide
                leaf all_community_exact-match {
                    type enumeration {
                        enum all_community_exact-match;
                    }
                }                  //all_community_exact-match
                leaf all_community_exact-match_wide {
                    type enumeration {
                        enum all_community_exact-match_wide;
                    }
                }                  //wide
                leaf all_community_json {
                    type enumeration {
                        enum all_community_json;
                    }
                }                  //all_community_json
                leaf all_community_json_detail {
                    type enumeration {
                        enum all_community_json_detail;
                    }
                }                  //detail
                leaf all_detail-routes_json {
                    type enumeration {
                        enum all_detail-routes_json;
                    }
                }                  //all_detail-routes_json
                leaf all_detail-routes_json_detail {
                    type enumeration {
                        enum all_detail-routes_json_detail;
                    }
                }                  //detail
                leaf all_summary_established {
                    type enumeration {
                        enum all_summary_established;
                    }
                }                  //all_summary_established
                leaf all_summary_established_neighbor {
                    type enumeration {
                        enum all_summary_established_neighbor;
                    }
                }                  //neighbor
                leaf all_summary_established_remote-as {
                    type enumeration {
                        enum all_summary_established_remote-as;
                    }
                }                  //remote-as
                leaf all_summary_established_json {
                    type enumeration {
                        enum all_summary_established_json;
                    }
                }                  //json
                leaf all_summary_failed {
                    type enumeration {
                        enum all_summary_failed;
                    }
                }                  //all_summary_failed
                leaf all_summary_failed_neighbor {
                    type enumeration {
                        enum all_summary_failed_neighbor;
                    }
                }                  //neighbor
                leaf all_summary_failed_remote-as {
                    type enumeration {
                        enum all_summary_failed_remote-as;
                    }
                }                  //remote-as
                leaf all_summary_failed_json {
                    type enumeration {
                        enum all_summary_failed_json;
                    }
                }                  //json
                leaf all_summary_terse {
                    type enumeration {
                        enum all_summary_terse;
                    }
                }                  //all_summary_terse
                leaf all_summary_terse_json {
                    type enumeration {
                        enum all_summary_terse_json;
                    }
                }                  //json
                leaf all_summary_wide {
                    type enumeration {
                        enum all_summary_wide;
                    }
                }                  //all_summary_wide
                leaf all_summary_wide_json {
                    type enumeration {
                        enum all_summary_wide_json;
                    }
                }                  //json
                leaf community_local-AS_exact-match {
                    type enumeration {
                        enum community_local-AS_exact-match;
                    }
                }                  //community_local-AS_exact-match
                leaf community_local-AS_exact-match_wide {
                    type enumeration {
                        enum community_local-AS_exact-match_wide;
                    }
                }                  //wide
                leaf community_local-AS_json {
                    type enumeration {
                        enum community_local-AS_json;
                    }
                }                  //community_local-AS_json
                leaf community_local-AS_json_detail {
                    type enumeration {
                        enum community_local-AS_json_detail;
                    }
                }                  //detail
                leaf community_no-advertise_exact-match {
                    type enumeration {
                        enum community_no-advertise_exact-match;
                    }
                }                  //community_no-advertise_exact-match
                leaf community_no-advertise_exact-match_wide {
                    type enumeration {
                        enum community_no-advertise_exact-match_wide;
                    }
                }                  //wide
                leaf community_no-advertise_json {
                    type enumeration {
                        enum community_no-advertise_json;
                    }
                }                  //community_no-advertise_json
                leaf community_no-advertise_json_detail {
                    type enumeration {
                        enum community_no-advertise_json_detail;
                    }
                }                  //detail
                leaf community_no-export_exact-match {
                    type enumeration {
                        enum community_no-export_exact-match;
                    }
                }                  //community_no-export_exact-match
                leaf community_no-export_exact-match_wide {
                    type enumeration {
                        enum community_no-export_exact-match_wide;
                    }
                }                  //wide
                leaf community_no-export_json {
                    type enumeration {
                        enum community_no-export_json;
                    }
                }                  //community_no-export_json
                leaf community_no-export_json_detail {
                    type enumeration {
                        enum community_no-export_json_detail;
                    }
                }                  //detail
                leaf community_graceful-shutdown_exact-match {
                    type enumeration {
                        enum community_graceful-shutdown_exact-match;
                    }
                }                  //community_graceful-shutdown_exact-match
                leaf community_graceful-shutdown_exact-match_wide {
                    type enumeration {
                        enum community_graceful-shutdown_exact-match_wide;
                    }
                }                  //wide
                leaf community_graceful-shutdown_json {
                    type enumeration {
                        enum community_graceful-shutdown_json;
                    }
                }                  //community_graceful-shutdown_json
                leaf community_graceful-shutdown_json_detail {
                    type enumeration {
                        enum community_graceful-shutdown_json_detail;
                    }
                }                  //detail
                leaf community_no-peer_exact-match {
                    type enumeration {
                        enum community_no-peer_exact-match;
                    }
                }                  //community_no-peer_exact-match
                leaf community_no-peer_exact-match_wide {
                    type enumeration {
                        enum community_no-peer_exact-match_wide;
                    }
                }                  //wide
                leaf community_no-peer_json {
                    type enumeration {
                        enum community_no-peer_json;
                    }
                }                  //community_no-peer_json
                leaf community_no-peer_json_detail {
                    type enumeration {
                        enum community_no-peer_json_detail;
                    }
                }                  //detail
                leaf community_blackhole_exact-match {
                    type enumeration {
                        enum community_blackhole_exact-match;
                    }
                }                  //community_blackhole_exact-match
                leaf community_blackhole_exact-match_wide {
                    type enumeration {
                        enum community_blackhole_exact-match_wide;
                    }
                }                  //wide
                leaf community_blackhole_json {
                    type enumeration {
                        enum community_blackhole_json;
                    }
                }                  //community_blackhole_json
                leaf community_blackhole_json_detail {
                    type enumeration {
                        enum community_blackhole_json_detail;
                    }
                }                  //detail
                leaf community_llgr-stale_exact-match {
                    type enumeration {
                        enum community_llgr-stale_exact-match;
                    }
                }                  //community_llgr-stale_exact-match
                leaf community_llgr-stale_exact-match_wide {
                    type enumeration {
                        enum community_llgr-stale_exact-match_wide;
                    }
                }                  //wide
                leaf community_llgr-stale_json {
                    type enumeration {
                        enum community_llgr-stale_json;
                    }
                }                  //community_llgr-stale_json
                leaf community_llgr-stale_json_detail {
                    type enumeration {
                        enum community_llgr-stale_json_detail;
                    }
                }                  //detail
                leaf community_no-llgr_exact-match {
                    type enumeration {
                        enum community_no-llgr_exact-match;
                    }
                }                  //community_no-llgr_exact-match
                leaf community_no-llgr_exact-match_wide {
                    type enumeration {
                        enum community_no-llgr_exact-match_wide;
                    }
                }                  //wide
                leaf community_no-llgr_json {
                    type enumeration {
                        enum community_no-llgr_json;
                    }
                }                  //community_no-llgr_json
                leaf community_no-llgr_json_detail {
                    type enumeration {
                        enum community_no-llgr_json_detail;
                    }
                }                  //detail
                leaf community_accept-own_exact-match {
                    type enumeration {
                        enum community_accept-own_exact-match;
                    }
                }                  //community_accept-own_exact-match
                leaf community_accept-own_exact-match_wide {
                    type enumeration {
                        enum community_accept-own_exact-match_wide;
                    }
                }                  //wide
                leaf community_accept-own_json {
                    type enumeration {
                        enum community_accept-own_json;
                    }
                }                  //community_accept-own_json
                leaf community_accept-own_json_detail {
                    type enumeration {
                        enum community_accept-own_json_detail;
                    }
                }                  //detail
                leaf community_accept-own-nexthop_exact-match {
                    type enumeration {
                        enum community_accept-own-nexthop_exact-match;
                    }
                }                  //community_accept-own-nexthop_exact-match
                leaf community_accept-own-nexthop_exact-match_wide {
                    type enumeration {
                        enum community_accept-own-nexthop_exact-match_wide;
                    }
                }                  //wide
                leaf community_accept-own-nexthop_json {
                    type enumeration {
                        enum community_accept-own-nexthop_json;
                    }
                }                  //community_accept-own-nexthop_json
                leaf community_accept-own-nexthop_json_detail {
                    type enumeration {
                        enum community_accept-own-nexthop_json_detail;
                    }
                }                  //detail
                leaf community_route-filter-v6_exact-match {
                    type enumeration {
                        enum community_route-filter-v6_exact-match;
                    }
                }                  //community_route-filter-v6_exact-match
                leaf community_route-filter-v6_exact-match_wide {
                    type enumeration {
                        enum community_route-filter-v6_exact-match_wide;
                    }
                }                  //wide
                leaf community_route-filter-v6_json {
                    type enumeration {
                        enum community_route-filter-v6_json;
                    }
                }                  //community_route-filter-v6_json
                leaf community_route-filter-v6_json_detail {
                    type enumeration {
                        enum community_route-filter-v6_json_detail;
                    }
                }                  //detail
                leaf community_route-filter-v4_exact-match {
                    type enumeration {
                        enum community_route-filter-v4_exact-match;
                    }
                }                  //community_route-filter-v4_exact-match
                leaf community_route-filter-v4_exact-match_wide {
                    type enumeration {
                        enum community_route-filter-v4_exact-match_wide;
                    }
                }                  //wide
                leaf community_route-filter-v4_json {
                    type enumeration {
                        enum community_route-filter-v4_json;
                    }
                }                  //community_route-filter-v4_json
                leaf community_route-filter-v4_json_detail {
                    type enumeration {
                        enum community_route-filter-v4_json_detail;
                    }
                }                  //detail
                leaf community_route-filter-translated-v6_exact-match {
                    type enumeration {
                        enum community_route-filter-translated-v6_exact-match;
                    }
                }                  //community_route-filter-translated-v6_exact-match
                leaf community_route-filter-translated-v6_exact-match_wide {
                    type enumeration {
                        enum community_route-filter-translated-v6_exact-match_wide;
                    }
                }                  //wide
                leaf community_route-filter-translated-v6_json {
                    type enumeration {
                        enum community_route-filter-translated-v6_json;
                    }
                }                  //community_route-filter-translated-v6_json
                leaf community_route-filter-translated-v6_json_detail {
                    type enumeration {
                        enum community_route-filter-translated-v6_json_detail;
                    }
                }                  //detail
                leaf community_route-filter-translated-v4_exact-match {
                    type enumeration {
                        enum community_route-filter-translated-v4_exact-match;
                    }
                }                  //community_route-filter-translated-v4_exact-match
                leaf community_route-filter-translated-v4_exact-match_wide {
                    type enumeration {
                        enum community_route-filter-translated-v4_exact-match_wide;
                    }
                }                  //wide
                leaf community_route-filter-translated-v4_json {
                    type enumeration {
                        enum community_route-filter-translated-v4_json;
                    }
                }                  //community_route-filter-translated-v4_json
                leaf community_route-filter-translated-v4_json_detail {
                    type enumeration {
                        enum community_route-filter-translated-v4_json_detail;
                    }
                }                  //detail
                leaf community_exact-match_json {
                    type enumeration {
                        enum community_exact-match_json;
                    }
                }                  //community_exact-match_json
                leaf community_exact-match_json_detail {
                    type enumeration {
                        enum community_exact-match_json_detail;
                    }
                }                  //detail
                leaf summary_established_terse {
                    type enumeration {
                        enum summary_established_terse;
                    }
                }                  //summary_established_terse
                leaf summary_established_terse_json {
                    type enumeration {
                        enum summary_established_terse_json;
                    }
                }                  //json
                leaf summary_established_wide {
                    type enumeration {
                        enum summary_established_wide;
                    }
                }                  //summary_established_wide
                leaf summary_established_wide_json {
                    type enumeration {
                        enum summary_established_wide_json;
                    }
                }                  //json
                leaf summary_failed_terse {
                    type enumeration {
                        enum summary_failed_terse;
                    }
                }                  //summary_failed_terse
                leaf summary_failed_terse_json {
                    type enumeration {
                        enum summary_failed_terse_json;
                    }
                }                  //json
                leaf summary_failed_wide {
                    type enumeration {
                        enum summary_failed_wide;
                    }
                }                  //summary_failed_wide
                leaf summary_failed_wide_json {
                    type enumeration {
                        enum summary_failed_wide_json;
                    }
                }                  //json
                leaf summary_terse_wide {
                    type enumeration {
                        enum summary_terse_wide;
                    }
                }                  //summary_terse_wide
                leaf summary_terse_wide_json {
                    type enumeration {
                        enum summary_terse_wide_json;
                    }
                }                  //json
                leaf all_community_local-AS_exact-match {
                    type enumeration {
                        enum all_community_local-AS_exact-match;
                    }
                }                  //all_community_local-AS_exact-match
                leaf all_community_local-AS_exact-match_wide {
                    type enumeration {
                        enum all_community_local-AS_exact-match_wide;
                    }
                }                  //wide
                leaf all_community_local-AS_json {
                    type enumeration {
                        enum all_community_local-AS_json;
                    }
                }                  //all_community_local-AS_json
                leaf all_community_local-AS_json_detail {
                    type enumeration {
                        enum all_community_local-AS_json_detail;
                    }
                }                  //detail
                leaf all_community_no-advertise_exact-match {
                    type enumeration {
                        enum all_community_no-advertise_exact-match;
                    }
                }                  //all_community_no-advertise_exact-match
                leaf all_community_no-advertise_exact-match_wide {
                    type enumeration {
                        enum all_community_no-advertise_exact-match_wide;
                    }
                }                  //wide
                leaf all_community_no-advertise_json {
                    type enumeration {
                        enum all_community_no-advertise_json;
                    }
                }                  //all_community_no-advertise_json
                leaf all_community_no-advertise_json_detail {
                    type enumeration {
                        enum all_community_no-advertise_json_detail;
                    }
                }                  //detail
                leaf all_community_no-export_exact-match {
                    type enumeration {
                        enum all_community_no-export_exact-match;
                    }
                }                  //all_community_no-export_exact-match
                leaf all_community_no-export_exact-match_wide {
                    type enumeration {
                        enum all_community_no-export_exact-match_wide;
                    }
                }                  //wide
                leaf all_community_no-export_json {
                    type enumeration {
                        enum all_community_no-export_json;
                    }
                }                  //all_community_no-export_json
                leaf all_community_no-export_json_detail {
                    type enumeration {
                        enum all_community_no-export_json_detail;
                    }
                }                  //detail
                leaf all_community_graceful-shutdown_exact-match {
                    type enumeration {
                        enum all_community_graceful-shutdown_exact-match;
                    }
                }                  //all_community_graceful-shutdown_exact-match
                leaf all_community_graceful-shutdown_exact-match_wide {
                    type enumeration {
                        enum all_community_graceful-shutdown_exact-match_wide;
                    }
                }                  //wide
                leaf all_community_graceful-shutdown_json {
                    type enumeration {
                        enum all_community_graceful-shutdown_json;
                    }
                }                  //all_community_graceful-shutdown_json
                leaf all_community_graceful-shutdown_json_detail {
                    type enumeration {
                        enum all_community_graceful-shutdown_json_detail;
                    }
                }                  //detail
                leaf all_community_no-peer_exact-match {
                    type enumeration {
                        enum all_community_no-peer_exact-match;
                    }
                }                  //all_community_no-peer_exact-match
                leaf all_community_no-peer_exact-match_wide {
                    type enumeration {
                        enum all_community_no-peer_exact-match_wide;
                    }
                }                  //wide
                leaf all_community_no-peer_json {
                    type enumeration {
                        enum all_community_no-peer_json;
                    }
                }                  //all_community_no-peer_json
                leaf all_community_no-peer_json_detail {
                    type enumeration {
                        enum all_community_no-peer_json_detail;
                    }
                }                  //detail
                leaf all_community_blackhole_exact-match {
                    type enumeration {
                        enum all_community_blackhole_exact-match;
                    }
                }                  //all_community_blackhole_exact-match
                leaf all_community_blackhole_exact-match_wide {
                    type enumeration {
                        enum all_community_blackhole_exact-match_wide;
                    }
                }                  //wide
                leaf all_community_blackhole_json {
                    type enumeration {
                        enum all_community_blackhole_json;
                    }
                }                  //all_community_blackhole_json
                leaf all_community_blackhole_json_detail {
                    type enumeration {
                        enum all_community_blackhole_json_detail;
                    }
                }                  //detail
                leaf all_community_llgr-stale_exact-match {
                    type enumeration {
                        enum all_community_llgr-stale_exact-match;
                    }
                }                  //all_community_llgr-stale_exact-match
                leaf all_community_llgr-stale_exact-match_wide {
                    type enumeration {
                        enum all_community_llgr-stale_exact-match_wide;
                    }
                }                  //wide
                leaf all_community_llgr-stale_json {
                    type enumeration {
                        enum all_community_llgr-stale_json;
                    }
                }                  //all_community_llgr-stale_json
                leaf all_community_llgr-stale_json_detail {
                    type enumeration {
                        enum all_community_llgr-stale_json_detail;
                    }
                }                  //detail
                leaf all_community_no-llgr_exact-match {
                    type enumeration {
                        enum all_community_no-llgr_exact-match;
                    }
                }                  //all_community_no-llgr_exact-match
                leaf all_community_no-llgr_exact-match_wide {
                    type enumeration {
                        enum all_community_no-llgr_exact-match_wide;
                    }
                }                  //wide
                leaf all_community_no-llgr_json {
                    type enumeration {
                        enum all_community_no-llgr_json;
                    }
                }                  //all_community_no-llgr_json
                leaf all_community_no-llgr_json_detail {
                    type enumeration {
                        enum all_community_no-llgr_json_detail;
                    }
                }                  //detail
                leaf all_community_accept-own_exact-match {
                    type enumeration {
                        enum all_community_accept-own_exact-match;
                    }
                }                  //all_community_accept-own_exact-match
                leaf all_community_accept-own_exact-match_wide {
                    type enumeration {
                        enum all_community_accept-own_exact-match_wide;
                    }
                }                  //wide
                leaf all_community_accept-own_json {
                    type enumeration {
                        enum all_community_accept-own_json;
                    }
                }                  //all_community_accept-own_json
                leaf all_community_accept-own_json_detail {
                    type enumeration {
                        enum all_community_accept-own_json_detail;
                    }
                }                  //detail
                leaf all_community_accept-own-nexthop_exact-match {
                    type enumeration {
                        enum all_community_accept-own-nexthop_exact-match;
                    }
                }                  //all_community_accept-own-nexthop_exact-match
                leaf all_community_accept-own-nexthop_exact-match_wide {
                    type enumeration {
                        enum all_community_accept-own-nexthop_exact-match_wide;
                    }
                }                  //wide
                leaf all_community_accept-own-nexthop_json {
                    type enumeration {
                        enum all_community_accept-own-nexthop_json;
                    }
                }                  //all_community_accept-own-nexthop_json
                leaf all_community_accept-own-nexthop_json_detail {
                    type enumeration {
                        enum all_community_accept-own-nexthop_json_detail;
                    }
                }                  //detail
                leaf all_community_route-filter-v6_exact-match {
                    type enumeration {
                        enum all_community_route-filter-v6_exact-match;
                    }
                }                  //all_community_route-filter-v6_exact-match
                leaf all_community_route-filter-v6_exact-match_wide {
                    type enumeration {
                        enum all_community_route-filter-v6_exact-match_wide;
                    }
                }                  //wide
                leaf all_community_route-filter-v6_json {
                    type enumeration {
                        enum all_community_route-filter-v6_json;
                    }
                }                  //all_community_route-filter-v6_json
                leaf all_community_route-filter-v6_json_detail {
                    type enumeration {
                        enum all_community_route-filter-v6_json_detail;
                    }
                }                  //detail
                leaf all_community_route-filter-v4_exact-match {
                    type enumeration {
                        enum all_community_route-filter-v4_exact-match;
                    }
                }                  //all_community_route-filter-v4_exact-match
                leaf all_community_route-filter-v4_exact-match_wide {
                    type enumeration {
                        enum all_community_route-filter-v4_exact-match_wide;
                    }
                }                  //wide
                leaf all_community_route-filter-v4_json {
                    type enumeration {
                        enum all_community_route-filter-v4_json;
                    }
                }                  //all_community_route-filter-v4_json
                leaf all_community_route-filter-v4_json_detail {
                    type enumeration {
                        enum all_community_route-filter-v4_json_detail;
                    }
                }                  //detail
                leaf all_community_route-filter-translated-v6_exact-match {
                    type enumeration {
                        enum all_community_route-filter-translated-v6_exact-match;
                    }
                }                  //all_community_route-filter-translated-v6_exact-match
                leaf all_community_route-filter-translated-v6_exact-match_wide {
                    type enumeration {
                        enum all_community_route-filter-translated-v6_exact-match_wide;
                    }
                }                  //wide
                leaf all_community_route-filter-translated-v6_json {
                    type enumeration {
                        enum all_community_route-filter-translated-v6_json;
                    }
                }                  //all_community_route-filter-translated-v6_json
                leaf all_community_route-filter-translated-v6_json_detail {
                    type enumeration {
                        enum all_community_route-filter-translated-v6_json_detail;
                    }
                }                  //detail
                leaf all_community_route-filter-translated-v4_exact-match {
                    type enumeration {
                        enum all_community_route-filter-translated-v4_exact-match;
                    }
                }                  //all_community_route-filter-translated-v4_exact-match
                leaf all_community_route-filter-translated-v4_exact-match_wide {
                    type enumeration {
                        enum all_community_route-filter-translated-v4_exact-match_wide;
                    }
                }                  //wide
                leaf all_community_route-filter-translated-v4_json {
                    type enumeration {
                        enum all_community_route-filter-translated-v4_json;
                    }
                }                  //all_community_route-filter-translated-v4_json
                leaf all_community_route-filter-translated-v4_json_detail {
                    type enumeration {
                        enum all_community_route-filter-translated-v4_json_detail;
                    }
                }                  //detail
                leaf all_community_exact-match_json {
                    type enumeration {
                        enum all_community_exact-match_json;
                    }
                }                  //all_community_exact-match_json
                leaf all_community_exact-match_json_detail {
                    type enumeration {
                        enum all_community_exact-match_json_detail;
                    }
                }                  //detail
                leaf all_summary_established_terse {
                    type enumeration {
                        enum all_summary_established_terse;
                    }
                }                  //all_summary_established_terse
                leaf all_summary_established_terse_json {
                    type enumeration {
                        enum all_summary_established_terse_json;
                    }
                }                  //json
                leaf all_summary_established_wide {
                    type enumeration {
                        enum all_summary_established_wide;
                    }
                }                  //all_summary_established_wide
                leaf all_summary_established_wide_json {
                    type enumeration {
                        enum all_summary_established_wide_json;
                    }
                }                  //json
                leaf all_summary_failed_terse {
                    type enumeration {
                        enum all_summary_failed_terse;
                    }
                }                  //all_summary_failed_terse
                leaf all_summary_failed_terse_json {
                    type enumeration {
                        enum all_summary_failed_terse_json;
                    }
                }                  //json
                leaf all_summary_failed_wide {
                    type enumeration {
                        enum all_summary_failed_wide;
                    }
                }                  //all_summary_failed_wide
                leaf all_summary_failed_wide_json {
                    type enumeration {
                        enum all_summary_failed_wide_json;
                    }
                }                  //json
                leaf all_summary_terse_wide {
                    type enumeration {
                        enum all_summary_terse_wide;
                    }
                }                  //all_summary_terse_wide
                leaf all_summary_terse_wide_json {
                    type enumeration {
                        enum all_summary_terse_wide_json;
                    }
                }                  //json
                leaf community_local-AS_exact-match_json {
                    type enumeration {
                        enum community_local-AS_exact-match_json;
                    }
                }                  //community_local-AS_exact-match_json
                leaf community_local-AS_exact-match_json_detail {
                    type enumeration {
                        enum community_local-AS_exact-match_json_detail;
                    }
                }                  //detail
                leaf community_no-advertise_exact-match_json {
                    type enumeration {
                        enum community_no-advertise_exact-match_json;
                    }
                }                  //community_no-advertise_exact-match_json
                leaf community_no-advertise_exact-match_json_detail {
                    type enumeration {
                        enum community_no-advertise_exact-match_json_detail;
                    }
                }                  //detail
                leaf community_no-export_exact-match_json {
                    type enumeration {
                        enum community_no-export_exact-match_json;
                    }
                }                  //community_no-export_exact-match_json
                leaf community_no-export_exact-match_json_detail {
                    type enumeration {
                        enum community_no-export_exact-match_json_detail;
                    }
                }                  //detail
                leaf community_graceful-shutdown_exact-match_json {
                    type enumeration {
                        enum community_graceful-shutdown_exact-match_json;
                    }
                }                  //community_graceful-shutdown_exact-match_json
                leaf community_graceful-shutdown_exact-match_json_detail {
                    type enumeration {
                        enum community_graceful-shutdown_exact-match_json_detail;
                    }
                }                  //detail
                leaf community_no-peer_exact-match_json {
                    type enumeration {
                        enum community_no-peer_exact-match_json;
                    }
                }                  //community_no-peer_exact-match_json
                leaf community_no-peer_exact-match_json_detail {
                    type enumeration {
                        enum community_no-peer_exact-match_json_detail;
                    }
                }                  //detail
                leaf community_blackhole_exact-match_json {
                    type enumeration {
                        enum community_blackhole_exact-match_json;
                    }
                }                  //community_blackhole_exact-match_json
                leaf community_blackhole_exact-match_json_detail {
                    type enumeration {
                        enum community_blackhole_exact-match_json_detail;
                    }
                }                  //detail
                leaf community_llgr-stale_exact-match_json {
                    type enumeration {
                        enum community_llgr-stale_exact-match_json;
                    }
                }                  //community_llgr-stale_exact-match_json
                leaf community_llgr-stale_exact-match_json_detail {
                    type enumeration {
                        enum community_llgr-stale_exact-match_json_detail;
                    }
                }                  //detail
                leaf community_no-llgr_exact-match_json {
                    type enumeration {
                        enum community_no-llgr_exact-match_json;
                    }
                }                  //community_no-llgr_exact-match_json
                leaf community_no-llgr_exact-match_json_detail {
                    type enumeration {
                        enum community_no-llgr_exact-match_json_detail;
                    }
                }                  //detail
                leaf community_accept-own_exact-match_json {
                    type enumeration {
                        enum community_accept-own_exact-match_json;
                    }
                }                  //community_accept-own_exact-match_json
                leaf community_accept-own_exact-match_json_detail {
                    type enumeration {
                        enum community_accept-own_exact-match_json_detail;
                    }
                }                  //detail
                leaf community_accept-own-nexthop_exact-match_json {
                    type enumeration {
                        enum community_accept-own-nexthop_exact-match_json;
                    }
                }                  //community_accept-own-nexthop_exact-match_json
                leaf community_accept-own-nexthop_exact-match_json_detail {
                    type enumeration {
                        enum community_accept-own-nexthop_exact-match_json_detail;
                    }
                }                  //detail
                leaf community_route-filter-v6_exact-match_json {
                    type enumeration {
                        enum community_route-filter-v6_exact-match_json;
                    }
                }                  //community_route-filter-v6_exact-match_json
                leaf community_route-filter-v6_exact-match_json_detail {
                    type enumeration {
                        enum community_route-filter-v6_exact-match_json_detail;
                    }
                }                  //detail
                leaf community_route-filter-v4_exact-match_json {
                    type enumeration {
                        enum community_route-filter-v4_exact-match_json;
                    }
                }                  //community_route-filter-v4_exact-match_json
                leaf community_route-filter-v4_exact-match_json_detail {
                    type enumeration {
                        enum community_route-filter-v4_exact-match_json_detail;
                    }
                }                  //detail
                leaf community_route-filter-translated-v6_exact-match_json {
                    type enumeration {
                        enum community_route-filter-translated-v6_exact-match_json;
                    }
                }                  //community_route-filter-translated-v6_exact-match_json
                leaf community_route-filter-translated-v6_exact-match_json_detail {
                    type enumeration {
                        enum community_route-filter-translated-v6_exact-match_json_detail;
                    }
                }                  //detail
                leaf community_route-filter-translated-v4_exact-match_json {
                    type enumeration {
                        enum community_route-filter-translated-v4_exact-match_json;
                    }
                }                  //community_route-filter-translated-v4_exact-match_json
                leaf community_route-filter-translated-v4_exact-match_json_detail {
                    type enumeration {
                        enum community_route-filter-translated-v4_exact-match_json_detail;
                    }
                }                  //detail
                leaf summary_established_terse_wide {
                    type enumeration {
                        enum summary_established_terse_wide;
                    }
                }                  //summary_established_terse_wide
                leaf summary_established_terse_wide_json {
                    type enumeration {
                        enum summary_established_terse_wide_json;
                    }
                }                  //json
                leaf summary_failed_terse_wide {
                    type enumeration {
                        enum summary_failed_terse_wide;
                    }
                }                  //summary_failed_terse_wide
                leaf summary_failed_terse_wide_json {
                    type enumeration {
                        enum summary_failed_terse_wide_json;
                    }
                }                  //json
                leaf all_community_local-AS_exact-match_json {
                    type enumeration {
                        enum all_community_local-AS_exact-match_json;
                    }
                }                  //all_community_local-AS_exact-match_json
                leaf all_community_local-AS_exact-match_json_detail {
                    type enumeration {
                        enum all_community_local-AS_exact-match_json_detail;
                    }
                }                  //detail
                leaf all_community_no-advertise_exact-match_json {
                    type enumeration {
                        enum all_community_no-advertise_exact-match_json;
                    }
                }                  //all_community_no-advertise_exact-match_json
                leaf all_community_no-advertise_exact-match_json_detail {
                    type enumeration {
                        enum all_community_no-advertise_exact-match_json_detail;
                    }
                }                  //detail
                leaf all_community_no-export_exact-match_json {
                    type enumeration {
                        enum all_community_no-export_exact-match_json;
                    }
                }                  //all_community_no-export_exact-match_json
                leaf all_community_no-export_exact-match_json_detail {
                    type enumeration {
                        enum all_community_no-export_exact-match_json_detail;
                    }
                }                  //detail
                leaf all_community_graceful-shutdown_exact-match_json {
                    type enumeration {
                        enum all_community_graceful-shutdown_exact-match_json;
                    }
                }                  //all_community_graceful-shutdown_exact-match_json
                leaf all_community_graceful-shutdown_exact-match_json_detail {
                    type enumeration {
                        enum all_community_graceful-shutdown_exact-match_json_detail;
                    }
                }                  //detail
                leaf all_community_no-peer_exact-match_json {
                    type enumeration {
                        enum all_community_no-peer_exact-match_json;
                    }
                }                  //all_community_no-peer_exact-match_json
                leaf all_community_no-peer_exact-match_json_detail {
                    type enumeration {
                        enum all_community_no-peer_exact-match_json_detail;
                    }
                }                  //detail
                leaf all_community_blackhole_exact-match_json {
                    type enumeration {
                        enum all_community_blackhole_exact-match_json;
                    }
                }                  //all_community_blackhole_exact-match_json
                leaf all_community_blackhole_exact-match_json_detail {
                    type enumeration {
                        enum all_community_blackhole_exact-match_json_detail;
                    }
                }                  //detail
                leaf all_community_llgr-stale_exact-match_json {
                    type enumeration {
                        enum all_community_llgr-stale_exact-match_json;
                    }
                }                  //all_community_llgr-stale_exact-match_json
                leaf all_community_llgr-stale_exact-match_json_detail {
                    type enumeration {
                        enum all_community_llgr-stale_exact-match_json_detail;
                    }
                }                  //detail
                leaf all_community_no-llgr_exact-match_json {
                    type enumeration {
                        enum all_community_no-llgr_exact-match_json;
                    }
                }                  //all_community_no-llgr_exact-match_json
                leaf all_community_no-llgr_exact-match_json_detail {
                    type enumeration {
                        enum all_community_no-llgr_exact-match_json_detail;
                    }
                }                  //detail
                leaf all_community_accept-own_exact-match_json {
                    type enumeration {
                        enum all_community_accept-own_exact-match_json;
                    }
                }                  //all_community_accept-own_exact-match_json
                leaf all_community_accept-own_exact-match_json_detail {
                    type enumeration {
                        enum all_community_accept-own_exact-match_json_detail;
                    }
                }                  //detail
                leaf all_community_accept-own-nexthop_exact-match_json {
                    type enumeration {
                        enum all_community_accept-own-nexthop_exact-match_json;
                    }
                }                  //all_community_accept-own-nexthop_exact-match_json
                leaf all_community_accept-own-nexthop_exact-match_json_detail {
                    type enumeration {
                        enum all_community_accept-own-nexthop_exact-match_json_detail;
                    }
                }                  //detail
                leaf all_community_route-filter-v6_exact-match_json {
                    type enumeration {
                        enum all_community_route-filter-v6_exact-match_json;
                    }
                }                  //all_community_route-filter-v6_exact-match_json
                leaf all_community_route-filter-v6_exact-match_json_detail {
                    type enumeration {
                        enum all_community_route-filter-v6_exact-match_json_detail;
                    }
                }                  //detail
                leaf all_community_route-filter-v4_exact-match_json {
                    type enumeration {
                        enum all_community_route-filter-v4_exact-match_json;
                    }
                }                  //all_community_route-filter-v4_exact-match_json
                leaf all_community_route-filter-v4_exact-match_json_detail {
                    type enumeration {
                        enum all_community_route-filter-v4_exact-match_json_detail;
                    }
                }                  //detail
                leaf all_community_route-filter-translated-v6_exact-match_json {
                    type enumeration {
                        enum all_community_route-filter-translated-v6_exact-match_json;
                    }
                }                  //all_community_route-filter-translated-v6_exact-match_json
                leaf all_community_route-filter-translated-v6_exact-match_json_detail {
                    type enumeration {
                        enum all_community_route-filter-translated-v6_exact-match_json_detail;
                    }
                }                  //detail
                leaf all_community_route-filter-translated-v4_exact-match_json {
                    type enumeration {
                        enum all_community_route-filter-translated-v4_exact-match_json;
                    }
                }                  //all_community_route-filter-translated-v4_exact-match_json
                leaf all_community_route-filter-translated-v4_exact-match_json_detail {
                    type enumeration {
                        enum all_community_route-filter-translated-v4_exact-match_json_detail;
                    }
                }                  //detail
                leaf all_summary_established_terse_wide {
                    type enumeration {
                        enum all_summary_established_terse_wide;
                    }
                }                  //all_summary_established_terse_wide
                leaf all_summary_established_terse_wide_json {
                    type enumeration {
                        enum all_summary_established_terse_wide_json;
                    }
                }                  //json
                leaf all_summary_failed_terse_wide {
                    type enumeration {
                        enum all_summary_failed_terse_wide;
                    }
                }                  //all_summary_failed_terse_wide
                leaf all_summary_failed_terse_wide_json {
                    type enumeration {
                        enum all_summary_failed_terse_wide_json;
                    }
                }                  //json
                leaf ADDRESS_FAMILY_MODIFIER {
                    type enumeration {
                        enum unicast;
                        enum multicast;
                        enum vpn;
                    }
                }                  //<unicast|multicast|vpn> ['Address Family modifier', 'Address Family modifier', 'Address Family modifier']
                leaf unicast_update-groups {
                    type enumeration {
                        enum unicast_update-groups;
                    }
                }                  //unicast_update-groups
                leaf SPECIFIC_SUBGROUP_TO_DISPLAY {
                    type string;
                }                  //SUBGROUP-ID
                leaf unicast_route-leak {
                    type enumeration {
                        enum unicast_route-leak;
                    }
                }                  //unicast_route-leak
                leaf unicast_route-leak_json {
                    type enumeration {
                        enum unicast_route-leak_json;
                    }
                }                  //json
                leaf flowspec_all {
                    type enumeration {
                        enum flowspec_all;
                    }
                }                  //flowspec_all
                leaf flowspec_all_community-list {
                    type enumeration {
                        enum flowspec_all_community-list;
                    }
                }                  //community-list
                leaf flowspec_all_filter-list {
                    type enumeration {
                        enum flowspec_all_filter-list;
                    }
                }                  //filter-list
                leaf flowspec_all_prefix-list {
                    type enumeration {
                        enum flowspec_all_prefix-list;
                    }
                }                  //prefix-list
                leaf flowspec_all_access-list {
                    type enumeration {
                        enum flowspec_all_access-list;
                    }
                }                  //access-list
                leaf flowspec_all_route-map {
                    type enumeration {
                        enum flowspec_all_route-map;
                    }
                }                  //route-map
                leaf flowspec_all_rpki {
                    type enumeration {
                        enum flowspec_all_rpki;
                    }
                }                  //rpki
                leaf flowspec_all_version {
                    type enumeration {
                        enum flowspec_all_version;
                    }
                }                  //version
                leaf flowspec_all_alias {
                    type enumeration {
                        enum flowspec_all_alias;
                    }
                }                  //alias
                leaf flowspec_all_wide {
                    type enumeration {
                        enum flowspec_all_wide;
                    }
                }                  //wide
                leaf flowspec_all_neighbors {
                    type enumeration {
                        enum flowspec_all_neighbors;
                    }
                }                  //neighbors
                leaf flowspec_cidr-only {
                    type enumeration {
                        enum flowspec_cidr-only;
                    }
                }                  //flowspec_cidr-only
                leaf flowspec_cidr-only_wide {
                    type enumeration {
                        enum flowspec_cidr-only_wide;
                    }
                }                  //wide
                leaf flowspec_dampening {
                    type enumeration {
                        enum flowspec_dampening;
                    }
                }                  //flowspec_dampening
                leaf flowspec_community {
                    type enumeration {
                        enum flowspec_community;
                    }
                }                  //flowspec_community
                leaf flowspec_community_wide {
                    type enumeration {
                        enum flowspec_community_wide;
                    }
                }                  //wide
                leaf flowspec_detail-routes {
                    type enumeration {
                        enum flowspec_detail-routes;
                    }
                }                  //flowspec_detail-routes
                leaf flowspec_detail-routes_wide {
                    type enumeration {
                        enum flowspec_detail-routes_wide;
                    }
                }                  //wide
                leaf flowspec_json {
                    type enumeration {
                        enum flowspec_json;
                    }
                }                  //flowspec_json
                leaf flowspec_json_detail {
                    type enumeration {
                        enum flowspec_json_detail;
                    }
                }                  //detail
                leaf flowspec_summary {
                    type enumeration {
                        enum flowspec_summary;
                    }
                }                  //flowspec_summary
                leaf flowspec_summary_neighbor {
                    type enumeration {
                        enum flowspec_summary_neighbor;
                    }
                }                  //neighbor
                leaf flowspec_summary_remote-as {
                    type enumeration {
                        enum flowspec_summary_remote-as;
                    }
                }                  //remote-as
                leaf flowspec_summary_json {
                    type enumeration {
                        enum flowspec_summary_json;
                    }
                }                  //json
                leaf flowspec_large-community {
                    type enumeration {
                        enum flowspec_large-community;
                    }
                }                  //flowspec_large-community
                leaf flowspec_large-community_json {
                    type enumeration {
                        enum flowspec_large-community_json;
                    }
                }                  //json
                leaf flowspec_statistics {
                    type enumeration {
                        enum flowspec_statistics;
                    }
                }                  //flowspec_statistics
                leaf flowspec_statistics_json {
                    type enumeration {
                        enum flowspec_statistics_json;
                    }
                }                  //json
                leaf flowspec_update-groups {
                    type enumeration {
                        enum flowspec_update-groups;
                    }
                }                  //flowspec_update-groups
                leaf flowspec_update-groups_json {
                    type enumeration {
                        enum flowspec_update-groups_json;
                    }
                }                  //json
                leaf flowspec_detail {
                    type enumeration {
                        enum flowspec_detail;
                    }
                }                  //flowspec_detail
                leaf flowspec_detail_json {
                    type enumeration {
                        enum flowspec_detail_json;
                    }
                }                  //json
                leaf flowspec_all_cidr-only {
                    type enumeration {
                        enum flowspec_all_cidr-only;
                    }
                }                  //flowspec_all_cidr-only
                leaf flowspec_all_cidr-only_wide {
                    type enumeration {
                        enum flowspec_all_cidr-only_wide;
                    }
                }                  //wide
                leaf flowspec_all_dampening {
                    type enumeration {
                        enum flowspec_all_dampening;
                    }
                }                  //flowspec_all_dampening
                leaf flowspec_all_community {
                    type enumeration {
                        enum flowspec_all_community;
                    }
                }                  //flowspec_all_community
                leaf flowspec_all_community_wide {
                    type enumeration {
                        enum flowspec_all_community_wide;
                    }
                }                  //wide
                leaf flowspec_all_detail-routes {
                    type enumeration {
                        enum flowspec_all_detail-routes;
                    }
                }                  //flowspec_all_detail-routes
                leaf flowspec_all_detail-routes_wide {
                    type enumeration {
                        enum flowspec_all_detail-routes_wide;
                    }
                }                  //wide
                leaf flowspec_all_json {
                    type enumeration {
                        enum flowspec_all_json;
                    }
                }                  //flowspec_all_json
                leaf flowspec_all_json_detail {
                    type enumeration {
                        enum flowspec_all_json_detail;
                    }
                }                  //detail
                leaf flowspec_all_summary {
                    type enumeration {
                        enum flowspec_all_summary;
                    }
                }                  //flowspec_all_summary
                leaf flowspec_all_summary_neighbor {
                    type enumeration {
                        enum flowspec_all_summary_neighbor;
                    }
                }                  //neighbor
                leaf flowspec_all_summary_remote-as {
                    type enumeration {
                        enum flowspec_all_summary_remote-as;
                    }
                }                  //remote-as
                leaf flowspec_all_summary_json {
                    type enumeration {
                        enum flowspec_all_summary_json;
                    }
                }                  //json
                leaf flowspec_cidr-only_json {
                    type enumeration {
                        enum flowspec_cidr-only_json;
                    }
                }                  //flowspec_cidr-only_json
                leaf flowspec_cidr-only_json_detail {
                    type enumeration {
                        enum flowspec_cidr-only_json_detail;
                    }
                }                  //detail
                leaf flowspec_dampening_parameters {
                    type enumeration {
                        enum flowspec_dampening_parameters;
                    }
                }                  //flowspec_dampening_parameters
                leaf flowspec_dampening_parameters_json {
                    type enumeration {
                        enum flowspec_dampening_parameters_json;
                    }
                }                  //json
                leaf flowspec_community_local-AS {
                    type enumeration {
                        enum flowspec_community_local-AS;
                    }
                }                  //flowspec_community_local-AS
                leaf flowspec_community_local-AS_wide {
                    type enumeration {
                        enum flowspec_community_local-AS_wide;
                    }
                }                  //wide
                leaf flowspec_community_no-advertise {
                    type enumeration {
                        enum flowspec_community_no-advertise;
                    }
                }                  //flowspec_community_no-advertise
                leaf flowspec_community_no-advertise_wide {
                    type enumeration {
                        enum flowspec_community_no-advertise_wide;
                    }
                }                  //wide
                leaf flowspec_community_no-export {
                    type enumeration {
                        enum flowspec_community_no-export;
                    }
                }                  //flowspec_community_no-export
                leaf flowspec_community_no-export_wide {
                    type enumeration {
                        enum flowspec_community_no-export_wide;
                    }
                }                  //wide
                leaf flowspec_community_graceful-shutdown {
                    type enumeration {
                        enum flowspec_community_graceful-shutdown;
                    }
                }                  //flowspec_community_graceful-shutdown
                leaf flowspec_community_graceful-shutdown_wide {
                    type enumeration {
                        enum flowspec_community_graceful-shutdown_wide;
                    }
                }                  //wide
                leaf flowspec_community_no-peer {
                    type enumeration {
                        enum flowspec_community_no-peer;
                    }
                }                  //flowspec_community_no-peer
                leaf flowspec_community_no-peer_wide {
                    type enumeration {
                        enum flowspec_community_no-peer_wide;
                    }
                }                  //wide
                leaf flowspec_community_blackhole {
                    type enumeration {
                        enum flowspec_community_blackhole;
                    }
                }                  //flowspec_community_blackhole
                leaf flowspec_community_blackhole_wide {
                    type enumeration {
                        enum flowspec_community_blackhole_wide;
                    }
                }                  //wide
                leaf flowspec_community_llgr-stale {
                    type enumeration {
                        enum flowspec_community_llgr-stale;
                    }
                }                  //flowspec_community_llgr-stale
                leaf flowspec_community_llgr-stale_wide {
                    type enumeration {
                        enum flowspec_community_llgr-stale_wide;
                    }
                }                  //wide
                leaf flowspec_community_no-llgr {
                    type enumeration {
                        enum flowspec_community_no-llgr;
                    }
                }                  //flowspec_community_no-llgr
                leaf flowspec_community_no-llgr_wide {
                    type enumeration {
                        enum flowspec_community_no-llgr_wide;
                    }
                }                  //wide
                leaf flowspec_community_accept-own {
                    type enumeration {
                        enum flowspec_community_accept-own;
                    }
                }                  //flowspec_community_accept-own
                leaf flowspec_community_accept-own_wide {
                    type enumeration {
                        enum flowspec_community_accept-own_wide;
                    }
                }                  //wide
                leaf flowspec_community_accept-own-nexthop {
                    type enumeration {
                        enum flowspec_community_accept-own-nexthop;
                    }
                }                  //flowspec_community_accept-own-nexthop
                leaf flowspec_community_accept-own-nexthop_wide {
                    type enumeration {
                        enum flowspec_community_accept-own-nexthop_wide;
                    }
                }                  //wide
                leaf flowspec_community_route-filter-v6 {
                    type enumeration {
                        enum flowspec_community_route-filter-v6;
                    }
                }                  //flowspec_community_route-filter-v6
                leaf flowspec_community_route-filter-v6_wide {
                    type enumeration {
                        enum flowspec_community_route-filter-v6_wide;
                    }
                }                  //wide
                leaf flowspec_community_route-filter-v4 {
                    type enumeration {
                        enum flowspec_community_route-filter-v4;
                    }
                }                  //flowspec_community_route-filter-v4
                leaf flowspec_community_route-filter-v4_wide {
                    type enumeration {
                        enum flowspec_community_route-filter-v4_wide;
                    }
                }                  //wide
                leaf flowspec_community_route-filter-translated-v6 {
                    type enumeration {
                        enum flowspec_community_route-filter-translated-v6;
                    }
                }                  //flowspec_community_route-filter-translated-v6
                leaf flowspec_community_route-filter-translated-v6_wide {
                    type enumeration {
                        enum flowspec_community_route-filter-translated-v6_wide;
                    }
                }                  //wide
                leaf flowspec_community_route-filter-translated-v4 {
                    type enumeration {
                        enum flowspec_community_route-filter-translated-v4;
                    }
                }                  //flowspec_community_route-filter-translated-v4
                leaf flowspec_community_route-filter-translated-v4_wide {
                    type enumeration {
                        enum flowspec_community_route-filter-translated-v4_wide;
                    }
                }                  //wide
                leaf flowspec_community_exact-match {
                    type enumeration {
                        enum flowspec_community_exact-match;
                    }
                }                  //flowspec_community_exact-match
                leaf flowspec_community_exact-match_wide {
                    type enumeration {
                        enum flowspec_community_exact-match_wide;
                    }
                }                  //wide
                leaf flowspec_community_json {
                    type enumeration {
                        enum flowspec_community_json;
                    }
                }                  //flowspec_community_json
                leaf flowspec_community_json_detail {
                    type enumeration {
                        enum flowspec_community_json_detail;
                    }
                }                  //detail
                leaf flowspec_detail-routes_json {
                    type enumeration {
                        enum flowspec_detail-routes_json;
                    }
                }                  //flowspec_detail-routes_json
                leaf flowspec_detail-routes_json_detail {
                    type enumeration {
                        enum flowspec_detail-routes_json_detail;
                    }
                }                  //detail
                leaf flowspec_summary_established {
                    type enumeration {
                        enum flowspec_summary_established;
                    }
                }                  //flowspec_summary_established
                leaf flowspec_summary_established_neighbor {
                    type enumeration {
                        enum flowspec_summary_established_neighbor;
                    }
                }                  //neighbor
                leaf flowspec_summary_established_remote-as {
                    type enumeration {
                        enum flowspec_summary_established_remote-as;
                    }
                }                  //remote-as
                leaf flowspec_summary_established_json {
                    type enumeration {
                        enum flowspec_summary_established_json;
                    }
                }                  //json
                leaf flowspec_summary_failed {
                    type enumeration {
                        enum flowspec_summary_failed;
                    }
                }                  //flowspec_summary_failed
                leaf flowspec_summary_failed_neighbor {
                    type enumeration {
                        enum flowspec_summary_failed_neighbor;
                    }
                }                  //neighbor
                leaf flowspec_summary_failed_remote-as {
                    type enumeration {
                        enum flowspec_summary_failed_remote-as;
                    }
                }                  //remote-as
                leaf flowspec_summary_failed_json {
                    type enumeration {
                        enum flowspec_summary_failed_json;
                    }
                }                  //json
                leaf flowspec_summary_terse {
                    type enumeration {
                        enum flowspec_summary_terse;
                    }
                }                  //flowspec_summary_terse
                leaf flowspec_summary_terse_json {
                    type enumeration {
                        enum flowspec_summary_terse_json;
                    }
                }                  //json
                leaf flowspec_summary_wide {
                    type enumeration {
                        enum flowspec_summary_wide;
                    }
                }                  //flowspec_summary_wide
                leaf flowspec_summary_wide_json {
                    type enumeration {
                        enum flowspec_summary_wide_json;
                    }
                }                  //json
                leaf flowspec_all_cidr-only_json {
                    type enumeration {
                        enum flowspec_all_cidr-only_json;
                    }
                }                  //flowspec_all_cidr-only_json
                leaf flowspec_all_cidr-only_json_detail {
                    type enumeration {
                        enum flowspec_all_cidr-only_json_detail;
                    }
                }                  //detail
                leaf flowspec_all_dampening_parameters {
                    type enumeration {
                        enum flowspec_all_dampening_parameters;
                    }
                }                  //flowspec_all_dampening_parameters
                leaf flowspec_all_dampening_parameters_json {
                    type enumeration {
                        enum flowspec_all_dampening_parameters_json;
                    }
                }                  //json
                leaf flowspec_all_community_local-AS {
                    type enumeration {
                        enum flowspec_all_community_local-AS;
                    }
                }                  //flowspec_all_community_local-AS
                leaf flowspec_all_community_local-AS_wide {
                    type enumeration {
                        enum flowspec_all_community_local-AS_wide;
                    }
                }                  //wide
                leaf flowspec_all_community_no-advertise {
                    type enumeration {
                        enum flowspec_all_community_no-advertise;
                    }
                }                  //flowspec_all_community_no-advertise
                leaf flowspec_all_community_no-advertise_wide {
                    type enumeration {
                        enum flowspec_all_community_no-advertise_wide;
                    }
                }                  //wide
                leaf flowspec_all_community_no-export {
                    type enumeration {
                        enum flowspec_all_community_no-export;
                    }
                }                  //flowspec_all_community_no-export
                leaf flowspec_all_community_no-export_wide {
                    type enumeration {
                        enum flowspec_all_community_no-export_wide;
                    }
                }                  //wide
                leaf flowspec_all_community_graceful-shutdown {
                    type enumeration {
                        enum flowspec_all_community_graceful-shutdown;
                    }
                }                  //flowspec_all_community_graceful-shutdown
                leaf flowspec_all_community_graceful-shutdown_wide {
                    type enumeration {
                        enum flowspec_all_community_graceful-shutdown_wide;
                    }
                }                  //wide
                leaf flowspec_all_community_no-peer {
                    type enumeration {
                        enum flowspec_all_community_no-peer;
                    }
                }                  //flowspec_all_community_no-peer
                leaf flowspec_all_community_no-peer_wide {
                    type enumeration {
                        enum flowspec_all_community_no-peer_wide;
                    }
                }                  //wide
                leaf flowspec_all_community_blackhole {
                    type enumeration {
                        enum flowspec_all_community_blackhole;
                    }
                }                  //flowspec_all_community_blackhole
                leaf flowspec_all_community_blackhole_wide {
                    type enumeration {
                        enum flowspec_all_community_blackhole_wide;
                    }
                }                  //wide
                leaf flowspec_all_community_llgr-stale {
                    type enumeration {
                        enum flowspec_all_community_llgr-stale;
                    }
                }                  //flowspec_all_community_llgr-stale
                leaf flowspec_all_community_llgr-stale_wide {
                    type enumeration {
                        enum flowspec_all_community_llgr-stale_wide;
                    }
                }                  //wide
                leaf flowspec_all_community_no-llgr {
                    type enumeration {
                        enum flowspec_all_community_no-llgr;
                    }
                }                  //flowspec_all_community_no-llgr
                leaf flowspec_all_community_no-llgr_wide {
                    type enumeration {
                        enum flowspec_all_community_no-llgr_wide;
                    }
                }                  //wide
                leaf flowspec_all_community_accept-own {
                    type enumeration {
                        enum flowspec_all_community_accept-own;
                    }
                }                  //flowspec_all_community_accept-own
                leaf flowspec_all_community_accept-own_wide {
                    type enumeration {
                        enum flowspec_all_community_accept-own_wide;
                    }
                }                  //wide
                leaf flowspec_all_community_accept-own-nexthop {
                    type enumeration {
                        enum flowspec_all_community_accept-own-nexthop;
                    }
                }                  //flowspec_all_community_accept-own-nexthop
                leaf flowspec_all_community_accept-own-nexthop_wide {
                    type enumeration {
                        enum flowspec_all_community_accept-own-nexthop_wide;
                    }
                }                  //wide
                leaf flowspec_all_community_route-filter-v6 {
                    type enumeration {
                        enum flowspec_all_community_route-filter-v6;
                    }
                }                  //flowspec_all_community_route-filter-v6
                leaf flowspec_all_community_route-filter-v6_wide {
                    type enumeration {
                        enum flowspec_all_community_route-filter-v6_wide;
                    }
                }                  //wide
                leaf flowspec_all_community_route-filter-v4 {
                    type enumeration {
                        enum flowspec_all_community_route-filter-v4;
                    }
                }                  //flowspec_all_community_route-filter-v4
                leaf flowspec_all_community_route-filter-v4_wide {
                    type enumeration {
                        enum flowspec_all_community_route-filter-v4_wide;
                    }
                }                  //wide
                leaf flowspec_all_community_route-filter-translated-v6 {
                    type enumeration {
                        enum flowspec_all_community_route-filter-translated-v6;
                    }
                }                  //flowspec_all_community_route-filter-translated-v6
                leaf flowspec_all_community_route-filter-translated-v6_wide {
                    type enumeration {
                        enum flowspec_all_community_route-filter-translated-v6_wide;
                    }
                }                  //wide
                leaf flowspec_all_community_route-filter-translated-v4 {
                    type enumeration {
                        enum flowspec_all_community_route-filter-translated-v4;
                    }
                }                  //flowspec_all_community_route-filter-translated-v4
                leaf flowspec_all_community_route-filter-translated-v4_wide {
                    type enumeration {
                        enum flowspec_all_community_route-filter-translated-v4_wide;
                    }
                }                  //wide
                leaf flowspec_all_community_exact-match {
                    type enumeration {
                        enum flowspec_all_community_exact-match;
                    }
                }                  //flowspec_all_community_exact-match
                leaf flowspec_all_community_exact-match_wide {
                    type enumeration {
                        enum flowspec_all_community_exact-match_wide;
                    }
                }                  //wide
                leaf flowspec_all_community_json {
                    type enumeration {
                        enum flowspec_all_community_json;
                    }
                }                  //flowspec_all_community_json
                leaf flowspec_all_community_json_detail {
                    type enumeration {
                        enum flowspec_all_community_json_detail;
                    }
                }                  //detail
                leaf flowspec_all_detail-routes_json {
                    type enumeration {
                        enum flowspec_all_detail-routes_json;
                    }
                }                  //flowspec_all_detail-routes_json
                leaf flowspec_all_detail-routes_json_detail {
                    type enumeration {
                        enum flowspec_all_detail-routes_json_detail;
                    }
                }                  //detail
                leaf flowspec_all_summary_established {
                    type enumeration {
                        enum flowspec_all_summary_established;
                    }
                }                  //flowspec_all_summary_established
                leaf flowspec_all_summary_established_neighbor {
                    type enumeration {
                        enum flowspec_all_summary_established_neighbor;
                    }
                }                  //neighbor
                leaf flowspec_all_summary_established_remote-as {
                    type enumeration {
                        enum flowspec_all_summary_established_remote-as;
                    }
                }                  //remote-as
                leaf flowspec_all_summary_established_json {
                    type enumeration {
                        enum flowspec_all_summary_established_json;
                    }
                }                  //json
                leaf flowspec_all_summary_failed {
                    type enumeration {
                        enum flowspec_all_summary_failed;
                    }
                }                  //flowspec_all_summary_failed
                leaf flowspec_all_summary_failed_neighbor {
                    type enumeration {
                        enum flowspec_all_summary_failed_neighbor;
                    }
                }                  //neighbor
                leaf flowspec_all_summary_failed_remote-as {
                    type enumeration {
                        enum flowspec_all_summary_failed_remote-as;
                    }
                }                  //remote-as
                leaf flowspec_all_summary_failed_json {
                    type enumeration {
                        enum flowspec_all_summary_failed_json;
                    }
                }                  //json
                leaf flowspec_all_summary_terse {
                    type enumeration {
                        enum flowspec_all_summary_terse;
                    }
                }                  //flowspec_all_summary_terse
                leaf flowspec_all_summary_terse_json {
                    type enumeration {
                        enum flowspec_all_summary_terse_json;
                    }
                }                  //json
                leaf flowspec_all_summary_wide {
                    type enumeration {
                        enum flowspec_all_summary_wide;
                    }
                }                  //flowspec_all_summary_wide
                leaf flowspec_all_summary_wide_json {
                    type enumeration {
                        enum flowspec_all_summary_wide_json;
                    }
                }                  //json
                leaf flowspec_community_local-AS_exact-match {
                    type enumeration {
                        enum flowspec_community_local-AS_exact-match;
                    }
                }                  //flowspec_community_local-AS_exact-match
                leaf flowspec_community_local-AS_exact-match_wide {
                    type enumeration {
                        enum flowspec_community_local-AS_exact-match_wide;
                    }
                }                  //wide
                leaf flowspec_community_local-AS_json {
                    type enumeration {
                        enum flowspec_community_local-AS_json;
                    }
                }                  //flowspec_community_local-AS_json
                leaf flowspec_community_local-AS_json_detail {
                    type enumeration {
                        enum flowspec_community_local-AS_json_detail;
                    }
                }                  //detail
                leaf flowspec_community_no-advertise_exact-match {
                    type enumeration {
                        enum flowspec_community_no-advertise_exact-match;
                    }
                }                  //flowspec_community_no-advertise_exact-match
                leaf flowspec_community_no-advertise_exact-match_wide {
                    type enumeration {
                        enum flowspec_community_no-advertise_exact-match_wide;
                    }
                }                  //wide
                leaf flowspec_community_no-advertise_json {
                    type enumeration {
                        enum flowspec_community_no-advertise_json;
                    }
                }                  //flowspec_community_no-advertise_json
                leaf flowspec_community_no-advertise_json_detail {
                    type enumeration {
                        enum flowspec_community_no-advertise_json_detail;
                    }
                }                  //detail
                leaf flowspec_community_no-export_exact-match {
                    type enumeration {
                        enum flowspec_community_no-export_exact-match;
                    }
                }                  //flowspec_community_no-export_exact-match
                leaf flowspec_community_no-export_exact-match_wide {
                    type enumeration {
                        enum flowspec_community_no-export_exact-match_wide;
                    }
                }                  //wide
                leaf flowspec_community_no-export_json {
                    type enumeration {
                        enum flowspec_community_no-export_json;
                    }
                }                  //flowspec_community_no-export_json
                leaf flowspec_community_no-export_json_detail {
                    type enumeration {
                        enum flowspec_community_no-export_json_detail;
                    }
                }                  //detail
                leaf flowspec_community_graceful-shutdown_exact-match {
                    type enumeration {
                        enum flowspec_community_graceful-shutdown_exact-match;
                    }
                }                  //flowspec_community_graceful-shutdown_exact-match
                leaf flowspec_community_graceful-shutdown_exact-match_wide {
                    type enumeration {
                        enum flowspec_community_graceful-shutdown_exact-match_wide;
                    }
                }                  //wide
                leaf flowspec_community_graceful-shutdown_json {
                    type enumeration {
                        enum flowspec_community_graceful-shutdown_json;
                    }
                }                  //flowspec_community_graceful-shutdown_json
                leaf flowspec_community_graceful-shutdown_json_detail {
                    type enumeration {
                        enum flowspec_community_graceful-shutdown_json_detail;
                    }
                }                  //detail
                leaf flowspec_community_no-peer_exact-match {
                    type enumeration {
                        enum flowspec_community_no-peer_exact-match;
                    }
                }                  //flowspec_community_no-peer_exact-match
                leaf flowspec_community_no-peer_exact-match_wide {
                    type enumeration {
                        enum flowspec_community_no-peer_exact-match_wide;
                    }
                }                  //wide
                leaf flowspec_community_no-peer_json {
                    type enumeration {
                        enum flowspec_community_no-peer_json;
                    }
                }                  //flowspec_community_no-peer_json
                leaf flowspec_community_no-peer_json_detail {
                    type enumeration {
                        enum flowspec_community_no-peer_json_detail;
                    }
                }                  //detail
                leaf flowspec_community_blackhole_exact-match {
                    type enumeration {
                        enum flowspec_community_blackhole_exact-match;
                    }
                }                  //flowspec_community_blackhole_exact-match
                leaf flowspec_community_blackhole_exact-match_wide {
                    type enumeration {
                        enum flowspec_community_blackhole_exact-match_wide;
                    }
                }                  //wide
                leaf flowspec_community_blackhole_json {
                    type enumeration {
                        enum flowspec_community_blackhole_json;
                    }
                }                  //flowspec_community_blackhole_json
                leaf flowspec_community_blackhole_json_detail {
                    type enumeration {
                        enum flowspec_community_blackhole_json_detail;
                    }
                }                  //detail
                leaf flowspec_community_llgr-stale_exact-match {
                    type enumeration {
                        enum flowspec_community_llgr-stale_exact-match;
                    }
                }                  //flowspec_community_llgr-stale_exact-match
                leaf flowspec_community_llgr-stale_exact-match_wide {
                    type enumeration {
                        enum flowspec_community_llgr-stale_exact-match_wide;
                    }
                }                  //wide
                leaf flowspec_community_llgr-stale_json {
                    type enumeration {
                        enum flowspec_community_llgr-stale_json;
                    }
                }                  //flowspec_community_llgr-stale_json
                leaf flowspec_community_llgr-stale_json_detail {
                    type enumeration {
                        enum flowspec_community_llgr-stale_json_detail;
                    }
                }                  //detail
                leaf flowspec_community_no-llgr_exact-match {
                    type enumeration {
                        enum flowspec_community_no-llgr_exact-match;
                    }
                }                  //flowspec_community_no-llgr_exact-match
                leaf flowspec_community_no-llgr_exact-match_wide {
                    type enumeration {
                        enum flowspec_community_no-llgr_exact-match_wide;
                    }
                }                  //wide
                leaf flowspec_community_no-llgr_json {
                    type enumeration {
                        enum flowspec_community_no-llgr_json;
                    }
                }                  //flowspec_community_no-llgr_json
                leaf flowspec_community_no-llgr_json_detail {
                    type enumeration {
                        enum flowspec_community_no-llgr_json_detail;
                    }
                }                  //detail
                leaf flowspec_community_accept-own_exact-match {
                    type enumeration {
                        enum flowspec_community_accept-own_exact-match;
                    }
                }                  //flowspec_community_accept-own_exact-match
                leaf flowspec_community_accept-own_exact-match_wide {
                    type enumeration {
                        enum flowspec_community_accept-own_exact-match_wide;
                    }
                }                  //wide
                leaf flowspec_community_accept-own_json {
                    type enumeration {
                        enum flowspec_community_accept-own_json;
                    }
                }                  //flowspec_community_accept-own_json
                leaf flowspec_community_accept-own_json_detail {
                    type enumeration {
                        enum flowspec_community_accept-own_json_detail;
                    }
                }                  //detail
                leaf flowspec_community_accept-own-nexthop_exact-match {
                    type enumeration {
                        enum flowspec_community_accept-own-nexthop_exact-match;
                    }
                }                  //flowspec_community_accept-own-nexthop_exact-match
                leaf flowspec_community_accept-own-nexthop_exact-match_wide {
                    type enumeration {
                        enum flowspec_community_accept-own-nexthop_exact-match_wide;
                    }
                }                  //wide
                leaf flowspec_community_accept-own-nexthop_json {
                    type enumeration {
                        enum flowspec_community_accept-own-nexthop_json;
                    }
                }                  //flowspec_community_accept-own-nexthop_json
                leaf flowspec_community_accept-own-nexthop_json_detail {
                    type enumeration {
                        enum flowspec_community_accept-own-nexthop_json_detail;
                    }
                }                  //detail
                leaf flowspec_community_route-filter-v6_exact-match {
                    type enumeration {
                        enum flowspec_community_route-filter-v6_exact-match;
                    }
                }                  //flowspec_community_route-filter-v6_exact-match
                leaf flowspec_community_route-filter-v6_exact-match_wide {
                    type enumeration {
                        enum flowspec_community_route-filter-v6_exact-match_wide;
                    }
                }                  //wide
                leaf flowspec_community_route-filter-v6_json {
                    type enumeration {
                        enum flowspec_community_route-filter-v6_json;
                    }
                }                  //flowspec_community_route-filter-v6_json
                leaf flowspec_community_route-filter-v6_json_detail {
                    type enumeration {
                        enum flowspec_community_route-filter-v6_json_detail;
                    }
                }                  //detail
                leaf flowspec_community_route-filter-v4_exact-match {
                    type enumeration {
                        enum flowspec_community_route-filter-v4_exact-match;
                    }
                }                  //flowspec_community_route-filter-v4_exact-match
                leaf flowspec_community_route-filter-v4_exact-match_wide {
                    type enumeration {
                        enum flowspec_community_route-filter-v4_exact-match_wide;
                    }
                }                  //wide
                leaf flowspec_community_route-filter-v4_json {
                    type enumeration {
                        enum flowspec_community_route-filter-v4_json;
                    }
                }                  //flowspec_community_route-filter-v4_json
                leaf flowspec_community_route-filter-v4_json_detail {
                    type enumeration {
                        enum flowspec_community_route-filter-v4_json_detail;
                    }
                }                  //detail
                leaf flowspec_community_route-filter-translated-v6_exact-match {
                    type enumeration {
                        enum flowspec_community_route-filter-translated-v6_exact-match;
                    }
                }                  //flowspec_community_route-filter-translated-v6_exact-match
                leaf flowspec_community_route-filter-translated-v6_exact-match_wide {
                    type enumeration {
                        enum flowspec_community_route-filter-translated-v6_exact-match_wide;
                    }
                }                  //wide
                leaf flowspec_community_route-filter-translated-v6_json {
                    type enumeration {
                        enum flowspec_community_route-filter-translated-v6_json;
                    }
                }                  //flowspec_community_route-filter-translated-v6_json
                leaf flowspec_community_route-filter-translated-v6_json_detail {
                    type enumeration {
                        enum flowspec_community_route-filter-translated-v6_json_detail;
                    }
                }                  //detail
                leaf flowspec_community_route-filter-translated-v4_exact-match {
                    type enumeration {
                        enum flowspec_community_route-filter-translated-v4_exact-match;
                    }
                }                  //flowspec_community_route-filter-translated-v4_exact-match
                leaf flowspec_community_route-filter-translated-v4_exact-match_wide {
                    type enumeration {
                        enum flowspec_community_route-filter-translated-v4_exact-match_wide;
                    }
                }                  //wide
                leaf flowspec_community_route-filter-translated-v4_json {
                    type enumeration {
                        enum flowspec_community_route-filter-translated-v4_json;
                    }
                }                  //flowspec_community_route-filter-translated-v4_json
                leaf flowspec_community_route-filter-translated-v4_json_detail {
                    type enumeration {
                        enum flowspec_community_route-filter-translated-v4_json_detail;
                    }
                }                  //detail
                leaf flowspec_community_exact-match_json {
                    type enumeration {
                        enum flowspec_community_exact-match_json;
                    }
                }                  //flowspec_community_exact-match_json
                leaf flowspec_community_exact-match_json_detail {
                    type enumeration {
                        enum flowspec_community_exact-match_json_detail;
                    }
                }                  //detail
                leaf flowspec_summary_established_terse {
                    type enumeration {
                        enum flowspec_summary_established_terse;
                    }
                }                  //flowspec_summary_established_terse
                leaf flowspec_summary_established_terse_json {
                    type enumeration {
                        enum flowspec_summary_established_terse_json;
                    }
                }                  //json
                leaf flowspec_summary_established_wide {
                    type enumeration {
                        enum flowspec_summary_established_wide;
                    }
                }                  //flowspec_summary_established_wide
                leaf flowspec_summary_established_wide_json {
                    type enumeration {
                        enum flowspec_summary_established_wide_json;
                    }
                }                  //json
                leaf flowspec_summary_failed_terse {
                    type enumeration {
                        enum flowspec_summary_failed_terse;
                    }
                }                  //flowspec_summary_failed_terse
                leaf flowspec_summary_failed_terse_json {
                    type enumeration {
                        enum flowspec_summary_failed_terse_json;
                    }
                }                  //json
                leaf flowspec_summary_failed_wide {
                    type enumeration {
                        enum flowspec_summary_failed_wide;
                    }
                }                  //flowspec_summary_failed_wide
                leaf flowspec_summary_failed_wide_json {
                    type enumeration {
                        enum flowspec_summary_failed_wide_json;
                    }
                }                  //json
                leaf flowspec_summary_terse_wide {
                    type enumeration {
                        enum flowspec_summary_terse_wide;
                    }
                }                  //flowspec_summary_terse_wide
                leaf flowspec_summary_terse_wide_json {
                    type enumeration {
                        enum flowspec_summary_terse_wide_json;
                    }
                }                  //json
                leaf flowspec_all_community_local-AS_exact-match {
                    type enumeration {
                        enum flowspec_all_community_local-AS_exact-match;
                    }
                }                  //flowspec_all_community_local-AS_exact-match
                leaf flowspec_all_community_local-AS_exact-match_wide {
                    type enumeration {
                        enum flowspec_all_community_local-AS_exact-match_wide;
                    }
                }                  //wide
                leaf flowspec_all_community_local-AS_json {
                    type enumeration {
                        enum flowspec_all_community_local-AS_json;
                    }
                }                  //flowspec_all_community_local-AS_json
                leaf flowspec_all_community_local-AS_json_detail {
                    type enumeration {
                        enum flowspec_all_community_local-AS_json_detail;
                    }
                }                  //detail
                leaf flowspec_all_community_no-advertise_exact-match {
                    type enumeration {
                        enum flowspec_all_community_no-advertise_exact-match;
                    }
                }                  //flowspec_all_community_no-advertise_exact-match
                leaf flowspec_all_community_no-advertise_exact-match_wide {
                    type enumeration {
                        enum flowspec_all_community_no-advertise_exact-match_wide;
                    }
                }                  //wide
                leaf flowspec_all_community_no-advertise_json {
                    type enumeration {
                        enum flowspec_all_community_no-advertise_json;
                    }
                }                  //flowspec_all_community_no-advertise_json
                leaf flowspec_all_community_no-advertise_json_detail {
                    type enumeration {
                        enum flowspec_all_community_no-advertise_json_detail;
                    }
                }                  //detail
                leaf flowspec_all_community_no-export_exact-match {
                    type enumeration {
                        enum flowspec_all_community_no-export_exact-match;
                    }
                }                  //flowspec_all_community_no-export_exact-match
                leaf flowspec_all_community_no-export_exact-match_wide {
                    type enumeration {
                        enum flowspec_all_community_no-export_exact-match_wide;
                    }
                }                  //wide
                leaf flowspec_all_community_no-export_json {
                    type enumeration {
                        enum flowspec_all_community_no-export_json;
                    }
                }                  //flowspec_all_community_no-export_json
                leaf flowspec_all_community_no-export_json_detail {
                    type enumeration {
                        enum flowspec_all_community_no-export_json_detail;
                    }
                }                  //detail
                leaf flowspec_all_community_graceful-shutdown_exact-match {
                    type enumeration {
                        enum flowspec_all_community_graceful-shutdown_exact-match;
                    }
                }                  //flowspec_all_community_graceful-shutdown_exact-match
                leaf flowspec_all_community_graceful-shutdown_exact-match_wide {
                    type enumeration {
                        enum flowspec_all_community_graceful-shutdown_exact-match_wide;
                    }
                }                  //wide
                leaf flowspec_all_community_graceful-shutdown_json {
                    type enumeration {
                        enum flowspec_all_community_graceful-shutdown_json;
                    }
                }                  //flowspec_all_community_graceful-shutdown_json
                leaf flowspec_all_community_graceful-shutdown_json_detail {
                    type enumeration {
                        enum flowspec_all_community_graceful-shutdown_json_detail;
                    }
                }                  //detail
                leaf flowspec_all_community_no-peer_exact-match {
                    type enumeration {
                        enum flowspec_all_community_no-peer_exact-match;
                    }
                }                  //flowspec_all_community_no-peer_exact-match
                leaf flowspec_all_community_no-peer_exact-match_wide {
                    type enumeration {
                        enum flowspec_all_community_no-peer_exact-match_wide;
                    }
                }                  //wide
                leaf flowspec_all_community_no-peer_json {
                    type enumeration {
                        enum flowspec_all_community_no-peer_json;
                    }
                }                  //flowspec_all_community_no-peer_json
                leaf flowspec_all_community_no-peer_json_detail {
                    type enumeration {
                        enum flowspec_all_community_no-peer_json_detail;
                    }
                }                  //detail
                leaf flowspec_all_community_blackhole_exact-match {
                    type enumeration {
                        enum flowspec_all_community_blackhole_exact-match;
                    }
                }                  //flowspec_all_community_blackhole_exact-match
                leaf flowspec_all_community_blackhole_exact-match_wide {
                    type enumeration {
                        enum flowspec_all_community_blackhole_exact-match_wide;
                    }
                }                  //wide
                leaf flowspec_all_community_blackhole_json {
                    type enumeration {
                        enum flowspec_all_community_blackhole_json;
                    }
                }                  //flowspec_all_community_blackhole_json
                leaf flowspec_all_community_blackhole_json_detail {
                    type enumeration {
                        enum flowspec_all_community_blackhole_json_detail;
                    }
                }                  //detail
                leaf flowspec_all_community_llgr-stale_exact-match {
                    type enumeration {
                        enum flowspec_all_community_llgr-stale_exact-match;
                    }
                }                  //flowspec_all_community_llgr-stale_exact-match
                leaf flowspec_all_community_llgr-stale_exact-match_wide {
                    type enumeration {
                        enum flowspec_all_community_llgr-stale_exact-match_wide;
                    }
                }                  //wide
                leaf flowspec_all_community_llgr-stale_json {
                    type enumeration {
                        enum flowspec_all_community_llgr-stale_json;
                    }
                }                  //flowspec_all_community_llgr-stale_json
                leaf flowspec_all_community_llgr-stale_json_detail {
                    type enumeration {
                        enum flowspec_all_community_llgr-stale_json_detail;
                    }
                }                  //detail
                leaf flowspec_all_community_no-llgr_exact-match {
                    type enumeration {
                        enum flowspec_all_community_no-llgr_exact-match;
                    }
                }                  //flowspec_all_community_no-llgr_exact-match
                leaf flowspec_all_community_no-llgr_exact-match_wide {
                    type enumeration {
                        enum flowspec_all_community_no-llgr_exact-match_wide;
                    }
                }                  //wide
                leaf flowspec_all_community_no-llgr_json {
                    type enumeration {
                        enum flowspec_all_community_no-llgr_json;
                    }
                }                  //flowspec_all_community_no-llgr_json
                leaf flowspec_all_community_no-llgr_json_detail {
                    type enumeration {
                        enum flowspec_all_community_no-llgr_json_detail;
                    }
                }                  //detail
                leaf flowspec_all_community_accept-own_exact-match {
                    type enumeration {
                        enum flowspec_all_community_accept-own_exact-match;
                    }
                }                  //flowspec_all_community_accept-own_exact-match
                leaf flowspec_all_community_accept-own_exact-match_wide {
                    type enumeration {
                        enum flowspec_all_community_accept-own_exact-match_wide;
                    }
                }                  //wide
                leaf flowspec_all_community_accept-own_json {
                    type enumeration {
                        enum flowspec_all_community_accept-own_json;
                    }
                }                  //flowspec_all_community_accept-own_json
                leaf flowspec_all_community_accept-own_json_detail {
                    type enumeration {
                        enum flowspec_all_community_accept-own_json_detail;
                    }
                }                  //detail
                leaf flowspec_all_community_accept-own-nexthop_exact-match {
                    type enumeration {
                        enum flowspec_all_community_accept-own-nexthop_exact-match;
                    }
                }                  //flowspec_all_community_accept-own-nexthop_exact-match
                leaf flowspec_all_community_accept-own-nexthop_exact-match_wide {
                    type enumeration {
                        enum flowspec_all_community_accept-own-nexthop_exact-match_wide;
                    }
                }                  //wide
                leaf flowspec_all_community_accept-own-nexthop_json {
                    type enumeration {
                        enum flowspec_all_community_accept-own-nexthop_json;
                    }
                }                  //flowspec_all_community_accept-own-nexthop_json
                leaf flowspec_all_community_accept-own-nexthop_json_detail {
                    type enumeration {
                        enum flowspec_all_community_accept-own-nexthop_json_detail;
                    }
                }                  //detail
                leaf flowspec_all_community_route-filter-v6_exact-match {
                    type enumeration {
                        enum flowspec_all_community_route-filter-v6_exact-match;
                    }
                }                  //flowspec_all_community_route-filter-v6_exact-match
                leaf flowspec_all_community_route-filter-v6_exact-match_wide {
                    type enumeration {
                        enum flowspec_all_community_route-filter-v6_exact-match_wide;
                    }
                }                  //wide
                leaf flowspec_all_community_route-filter-v6_json {
                    type enumeration {
                        enum flowspec_all_community_route-filter-v6_json;
                    }
                }                  //flowspec_all_community_route-filter-v6_json
                leaf flowspec_all_community_route-filter-v6_json_detail {
                    type enumeration {
                        enum flowspec_all_community_route-filter-v6_json_detail;
                    }
                }                  //detail
                leaf flowspec_all_community_route-filter-v4_exact-match {
                    type enumeration {
                        enum flowspec_all_community_route-filter-v4_exact-match;
                    }
                }                  //flowspec_all_community_route-filter-v4_exact-match
                leaf flowspec_all_community_route-filter-v4_exact-match_wide {
                    type enumeration {
                        enum flowspec_all_community_route-filter-v4_exact-match_wide;
                    }
                }                  //wide
                leaf flowspec_all_community_route-filter-v4_json {
                    type enumeration {
                        enum flowspec_all_community_route-filter-v4_json;
                    }
                }                  //flowspec_all_community_route-filter-v4_json
                leaf flowspec_all_community_route-filter-v4_json_detail {
                    type enumeration {
                        enum flowspec_all_community_route-filter-v4_json_detail;
                    }
                }                  //detail
                leaf flowspec_all_community_route-filter-translated-v6_exact-match {
                    type enumeration {
                        enum flowspec_all_community_route-filter-translated-v6_exact-match;
                    }
                }                  //flowspec_all_community_route-filter-translated-v6_exact-match
                leaf flowspec_all_community_route-filter-translated-v6_exact-match_wide {
                    type enumeration {
                        enum flowspec_all_community_route-filter-translated-v6_exact-match_wide;
                    }
                }                  //wide
                leaf flowspec_all_community_route-filter-translated-v6_json {
                    type enumeration {
                        enum flowspec_all_community_route-filter-translated-v6_json;
                    }
                }                  //flowspec_all_community_route-filter-translated-v6_json
                leaf flowspec_all_community_route-filter-translated-v6_json_detail {
                    type enumeration {
                        enum flowspec_all_community_route-filter-translated-v6_json_detail;
                    }
                }                  //detail
                leaf flowspec_all_community_route-filter-translated-v4_exact-match {
                    type enumeration {
                        enum flowspec_all_community_route-filter-translated-v4_exact-match;
                    }
                }                  //flowspec_all_community_route-filter-translated-v4_exact-match
                leaf flowspec_all_community_route-filter-translated-v4_exact-match_wide {
                    type enumeration {
                        enum flowspec_all_community_route-filter-translated-v4_exact-match_wide;
                    }
                }                  //wide
                leaf flowspec_all_community_route-filter-translated-v4_json {
                    type enumeration {
                        enum flowspec_all_community_route-filter-translated-v4_json;
                    }
                }                  //flowspec_all_community_route-filter-translated-v4_json
                leaf flowspec_all_community_route-filter-translated-v4_json_detail {
                    type enumeration {
                        enum flowspec_all_community_route-filter-translated-v4_json_detail;
                    }
                }                  //detail
                leaf flowspec_all_community_exact-match_json {
                    type enumeration {
                        enum flowspec_all_community_exact-match_json;
                    }
                }                  //flowspec_all_community_exact-match_json
                leaf flowspec_all_community_exact-match_json_detail {
                    type enumeration {
                        enum flowspec_all_community_exact-match_json_detail;
                    }
                }                  //detail
                leaf flowspec_all_summary_established_terse {
                    type enumeration {
                        enum flowspec_all_summary_established_terse;
                    }
                }                  //flowspec_all_summary_established_terse
                leaf flowspec_all_summary_established_terse_json {
                    type enumeration {
                        enum flowspec_all_summary_established_terse_json;
                    }
                }                  //json
                leaf flowspec_all_summary_established_wide {
                    type enumeration {
                        enum flowspec_all_summary_established_wide;
                    }
                }                  //flowspec_all_summary_established_wide
                leaf flowspec_all_summary_established_wide_json {
                    type enumeration {
                        enum flowspec_all_summary_established_wide_json;
                    }
                }                  //json
                leaf flowspec_all_summary_failed_terse {
                    type enumeration {
                        enum flowspec_all_summary_failed_terse;
                    }
                }                  //flowspec_all_summary_failed_terse
                leaf flowspec_all_summary_failed_terse_json {
                    type enumeration {
                        enum flowspec_all_summary_failed_terse_json;
                    }
                }                  //json
                leaf flowspec_all_summary_failed_wide {
                    type enumeration {
                        enum flowspec_all_summary_failed_wide;
                    }
                }                  //flowspec_all_summary_failed_wide
                leaf flowspec_all_summary_failed_wide_json {
                    type enumeration {
                        enum flowspec_all_summary_failed_wide_json;
                    }
                }                  //json
                leaf flowspec_all_summary_terse_wide {
                    type enumeration {
                        enum flowspec_all_summary_terse_wide;
                    }
                }                  //flowspec_all_summary_terse_wide
                leaf flowspec_all_summary_terse_wide_json {
                    type enumeration {
                        enum flowspec_all_summary_terse_wide_json;
                    }
                }                  //json
                leaf flowspec_community_local-AS_exact-match_json {
                    type enumeration {
                        enum flowspec_community_local-AS_exact-match_json;
                    }
                }                  //flowspec_community_local-AS_exact-match_json
                leaf flowspec_community_local-AS_exact-match_json_detail {
                    type enumeration {
                        enum flowspec_community_local-AS_exact-match_json_detail;
                    }
                }                  //detail
                leaf flowspec_community_no-advertise_exact-match_json {
                    type enumeration {
                        enum flowspec_community_no-advertise_exact-match_json;
                    }
                }                  //flowspec_community_no-advertise_exact-match_json
                leaf flowspec_community_no-advertise_exact-match_json_detail {
                    type enumeration {
                        enum flowspec_community_no-advertise_exact-match_json_detail;
                    }
                }                  //detail
                leaf flowspec_community_no-export_exact-match_json {
                    type enumeration {
                        enum flowspec_community_no-export_exact-match_json;
                    }
                }                  //flowspec_community_no-export_exact-match_json
                leaf flowspec_community_no-export_exact-match_json_detail {
                    type enumeration {
                        enum flowspec_community_no-export_exact-match_json_detail;
                    }
                }                  //detail
                leaf flowspec_community_graceful-shutdown_exact-match_json {
                    type enumeration {
                        enum flowspec_community_graceful-shutdown_exact-match_json;
                    }
                }                  //flowspec_community_graceful-shutdown_exact-match_json
                leaf flowspec_community_graceful-shutdown_exact-match_json_detail {
                    type enumeration {
                        enum flowspec_community_graceful-shutdown_exact-match_json_detail;
                    }
                }                  //detail
                leaf flowspec_community_no-peer_exact-match_json {
                    type enumeration {
                        enum flowspec_community_no-peer_exact-match_json;
                    }
                }                  //flowspec_community_no-peer_exact-match_json
                leaf flowspec_community_no-peer_exact-match_json_detail {
                    type enumeration {
                        enum flowspec_community_no-peer_exact-match_json_detail;
                    }
                }                  //detail
                leaf flowspec_community_blackhole_exact-match_json {
                    type enumeration {
                        enum flowspec_community_blackhole_exact-match_json;
                    }
                }                  //flowspec_community_blackhole_exact-match_json
                leaf flowspec_community_blackhole_exact-match_json_detail {
                    type enumeration {
                        enum flowspec_community_blackhole_exact-match_json_detail;
                    }
                }                  //detail
                leaf flowspec_community_llgr-stale_exact-match_json {
                    type enumeration {
                        enum flowspec_community_llgr-stale_exact-match_json;
                    }
                }                  //flowspec_community_llgr-stale_exact-match_json
                leaf flowspec_community_llgr-stale_exact-match_json_detail {
                    type enumeration {
                        enum flowspec_community_llgr-stale_exact-match_json_detail;
                    }
                }                  //detail
                leaf flowspec_community_no-llgr_exact-match_json {
                    type enumeration {
                        enum flowspec_community_no-llgr_exact-match_json;
                    }
                }                  //flowspec_community_no-llgr_exact-match_json
                leaf flowspec_community_no-llgr_exact-match_json_detail {
                    type enumeration {
                        enum flowspec_community_no-llgr_exact-match_json_detail;
                    }
                }                  //detail
                leaf flowspec_community_accept-own_exact-match_json {
                    type enumeration {
                        enum flowspec_community_accept-own_exact-match_json;
                    }
                }                  //flowspec_community_accept-own_exact-match_json
                leaf flowspec_community_accept-own_exact-match_json_detail {
                    type enumeration {
                        enum flowspec_community_accept-own_exact-match_json_detail;
                    }
                }                  //detail
                leaf flowspec_community_accept-own-nexthop_exact-match_json {
                    type enumeration {
                        enum flowspec_community_accept-own-nexthop_exact-match_json;
                    }
                }                  //flowspec_community_accept-own-nexthop_exact-match_json
                leaf flowspec_community_accept-own-nexthop_exact-match_json_detail {
                    type enumeration {
                        enum flowspec_community_accept-own-nexthop_exact-match_json_detail;
                    }
                }                  //detail
                leaf flowspec_community_route-filter-v6_exact-match_json {
                    type enumeration {
                        enum flowspec_community_route-filter-v6_exact-match_json;
                    }
                }                  //flowspec_community_route-filter-v6_exact-match_json
                leaf flowspec_community_route-filter-v6_exact-match_json_detail {
                    type enumeration {
                        enum flowspec_community_route-filter-v6_exact-match_json_detail;
                    }
                }                  //detail
                leaf flowspec_community_route-filter-v4_exact-match_json {
                    type enumeration {
                        enum flowspec_community_route-filter-v4_exact-match_json;
                    }
                }                  //flowspec_community_route-filter-v4_exact-match_json
                leaf flowspec_community_route-filter-v4_exact-match_json_detail {
                    type enumeration {
                        enum flowspec_community_route-filter-v4_exact-match_json_detail;
                    }
                }                  //detail
                leaf flowspec_community_route-filter-translated-v6_exact-match_json {
                    type enumeration {
                        enum flowspec_community_route-filter-translated-v6_exact-match_json;
                    }
                }                  //flowspec_community_route-filter-translated-v6_exact-match_json
                leaf flowspec_community_route-filter-translated-v6_exact-match_json_detail {
                    type enumeration {
                        enum flowspec_community_route-filter-translated-v6_exact-match_json_detail;
                    }
                }                  //detail
                leaf flowspec_community_route-filter-translated-v4_exact-match_json {
                    type enumeration {
                        enum flowspec_community_route-filter-translated-v4_exact-match_json;
                    }
                }                  //flowspec_community_route-filter-translated-v4_exact-match_json
                leaf flowspec_community_route-filter-translated-v4_exact-match_json_detail {
                    type enumeration {
                        enum flowspec_community_route-filter-translated-v4_exact-match_json_detail;
                    }
                }                  //detail
                leaf flowspec_summary_established_terse_wide {
                    type enumeration {
                        enum flowspec_summary_established_terse_wide;
                    }
                }                  //flowspec_summary_established_terse_wide
                leaf flowspec_summary_established_terse_wide_json {
                    type enumeration {
                        enum flowspec_summary_established_terse_wide_json;
                    }
                }                  //json
                leaf flowspec_summary_failed_terse_wide {
                    type enumeration {
                        enum flowspec_summary_failed_terse_wide;
                    }
                }                  //flowspec_summary_failed_terse_wide
                leaf flowspec_summary_failed_terse_wide_json {
                    type enumeration {
                        enum flowspec_summary_failed_terse_wide_json;
                    }
                }                  //json
                leaf flowspec_all_community_local-AS_exact-match_json {
                    type enumeration {
                        enum flowspec_all_community_local-AS_exact-match_json;
                    }
                }                  //flowspec_all_community_local-AS_exact-match_json
                leaf flowspec_all_community_local-AS_exact-match_json_detail {
                    type enumeration {
                        enum flowspec_all_community_local-AS_exact-match_json_detail;
                    }
                }                  //detail
                leaf flowspec_all_community_no-advertise_exact-match_json {
                    type enumeration {
                        enum flowspec_all_community_no-advertise_exact-match_json;
                    }
                }                  //flowspec_all_community_no-advertise_exact-match_json
                leaf flowspec_all_community_no-advertise_exact-match_json_detail {
                    type enumeration {
                        enum flowspec_all_community_no-advertise_exact-match_json_detail;
                    }
                }                  //detail
                leaf flowspec_all_community_no-export_exact-match_json {
                    type enumeration {
                        enum flowspec_all_community_no-export_exact-match_json;
                    }
                }                  //flowspec_all_community_no-export_exact-match_json
                leaf flowspec_all_community_no-export_exact-match_json_detail {
                    type enumeration {
                        enum flowspec_all_community_no-export_exact-match_json_detail;
                    }
                }                  //detail
                leaf flowspec_all_community_graceful-shutdown_exact-match_json {
                    type enumeration {
                        enum flowspec_all_community_graceful-shutdown_exact-match_json;
                    }
                }                  //flowspec_all_community_graceful-shutdown_exact-match_json
                leaf flowspec_all_community_graceful-shutdown_exact-match_json_detail {
                    type enumeration {
                        enum flowspec_all_community_graceful-shutdown_exact-match_json_detail;
                    }
                }                  //detail
                leaf flowspec_all_community_no-peer_exact-match_json {
                    type enumeration {
                        enum flowspec_all_community_no-peer_exact-match_json;
                    }
                }                  //flowspec_all_community_no-peer_exact-match_json
                leaf flowspec_all_community_no-peer_exact-match_json_detail {
                    type enumeration {
                        enum flowspec_all_community_no-peer_exact-match_json_detail;
                    }
                }                  //detail
                leaf flowspec_all_community_blackhole_exact-match_json {
                    type enumeration {
                        enum flowspec_all_community_blackhole_exact-match_json;
                    }
                }                  //flowspec_all_community_blackhole_exact-match_json
                leaf flowspec_all_community_blackhole_exact-match_json_detail {
                    type enumeration {
                        enum flowspec_all_community_blackhole_exact-match_json_detail;
                    }
                }                  //detail
                leaf flowspec_all_community_llgr-stale_exact-match_json {
                    type enumeration {
                        enum flowspec_all_community_llgr-stale_exact-match_json;
                    }
                }                  //flowspec_all_community_llgr-stale_exact-match_json
                leaf flowspec_all_community_llgr-stale_exact-match_json_detail {
                    type enumeration {
                        enum flowspec_all_community_llgr-stale_exact-match_json_detail;
                    }
                }                  //detail
                leaf flowspec_all_community_no-llgr_exact-match_json {
                    type enumeration {
                        enum flowspec_all_community_no-llgr_exact-match_json;
                    }
                }                  //flowspec_all_community_no-llgr_exact-match_json
                leaf flowspec_all_community_no-llgr_exact-match_json_detail {
                    type enumeration {
                        enum flowspec_all_community_no-llgr_exact-match_json_detail;
                    }
                }                  //detail
                leaf flowspec_all_community_accept-own_exact-match_json {
                    type enumeration {
                        enum flowspec_all_community_accept-own_exact-match_json;
                    }
                }                  //flowspec_all_community_accept-own_exact-match_json
                leaf flowspec_all_community_accept-own_exact-match_json_detail {
                    type enumeration {
                        enum flowspec_all_community_accept-own_exact-match_json_detail;
                    }
                }                  //detail
                leaf flowspec_all_community_accept-own-nexthop_exact-match_json {
                    type enumeration {
                        enum flowspec_all_community_accept-own-nexthop_exact-match_json;
                    }
                }                  //flowspec_all_community_accept-own-nexthop_exact-match_json
                leaf flowspec_all_community_accept-own-nexthop_exact-match_json_detail {
                    type enumeration {
                        enum flowspec_all_community_accept-own-nexthop_exact-match_json_detail;
                    }
                }                  //detail
                leaf flowspec_all_community_route-filter-v6_exact-match_json {
                    type enumeration {
                        enum flowspec_all_community_route-filter-v6_exact-match_json;
                    }
                }                  //flowspec_all_community_route-filter-v6_exact-match_json
                leaf flowspec_all_community_route-filter-v6_exact-match_json_detail {
                    type enumeration {
                        enum flowspec_all_community_route-filter-v6_exact-match_json_detail;
                    }
                }                  //detail
                leaf flowspec_all_community_route-filter-v4_exact-match_json {
                    type enumeration {
                        enum flowspec_all_community_route-filter-v4_exact-match_json;
                    }
                }                  //flowspec_all_community_route-filter-v4_exact-match_json
                leaf flowspec_all_community_route-filter-v4_exact-match_json_detail {
                    type enumeration {
                        enum flowspec_all_community_route-filter-v4_exact-match_json_detail;
                    }
                }                  //detail
                leaf flowspec_all_community_route-filter-translated-v6_exact-match_json {
                    type enumeration {
                        enum flowspec_all_community_route-filter-translated-v6_exact-match_json;
                    }
                }                  //flowspec_all_community_route-filter-translated-v6_exact-match_json
                leaf flowspec_all_community_route-filter-translated-v6_exact-match_json_detail {
                    type enumeration {
                        enum flowspec_all_community_route-filter-translated-v6_exact-match_json_detail;
                    }
                }                  //detail
                leaf flowspec_all_community_route-filter-translated-v4_exact-match_json {
                    type enumeration {
                        enum flowspec_all_community_route-filter-translated-v4_exact-match_json;
                    }
                }                  //flowspec_all_community_route-filter-translated-v4_exact-match_json
                leaf flowspec_all_community_route-filter-translated-v4_exact-match_json_detail {
                    type enumeration {
                        enum flowspec_all_community_route-filter-translated-v4_exact-match_json_detail;
                    }
                }                  //detail
                leaf flowspec_all_summary_established_terse_wide {
                    type enumeration {
                        enum flowspec_all_summary_established_terse_wide;
                    }
                }                  //flowspec_all_summary_established_terse_wide
                leaf flowspec_all_summary_established_terse_wide_json {
                    type enumeration {
                        enum flowspec_all_summary_established_terse_wide_json;
                    }
                }                  //json
                leaf flowspec_all_summary_failed_terse_wide {
                    type enumeration {
                        enum flowspec_all_summary_failed_terse_wide;
                    }
                }                  //flowspec_all_summary_failed_terse_wide
                leaf flowspec_all_summary_failed_terse_wide_json {
                    type enumeration {
                        enum flowspec_all_summary_failed_terse_wide_json;
                    }
                }                  //json
                leaf peer-group {
                    type enumeration {
                        enum peer-group;
                    }
                }                  //peer-group
                leaf peer-group_json {
                    type enumeration {
                        enum peer-group_json;
                    }
                }                  //json
                leaf statistics-all {
                    type enumeration {
                        enum statistics-all;
                    }
                }                  //statistics-all
                leaf statistics-all_json {
                    type enumeration {
                        enum statistics-all_json;
                    }
                }                  //json
                leaf l2vpn_evpn_statistics {
                    type enumeration {
                        enum l2vpn_evpn_statistics;
                    }
                }                  //l2vpn_evpn_statistics
                leaf l2vpn_evpn_statistics_json {
                    type enumeration {
                        enum l2vpn_evpn_statistics_json;
                    }
                }                  //json
                leaf all_update-groups {
                    type enumeration {
                        enum all_update-groups;
                    }
                }                  //all_update-groups
                leaf all_update-groups_json {
                    type enumeration {
                        enum all_update-groups_json;
                    }
                }                  //json
                leaf ADDRESS_FAMILY_TYPE {
                    type enumeration {
                        enum vpnv4;
                        enum vpnv6;
                    }
                }                  //<vpnv4|vpnv6> ['Address Family', 'Address Family']
                leaf all_tags {
                    type enumeration {
                        enum all_tags;
                    }
                }                  //tags
                leaf rd {
                    type enumeration {
                        enum rd;
                    }
                }                  //rd
                leaf BGP_IDENTIFIER {
                    type string;
                }                  //ASN:NN_OR_IP-ADDRESS:NN
                leaf tags {
                    type enumeration {
                        enum tags;
                    }
                }                  //tags
                leaf paths {
                    type enumeration {
                        enum paths;
                    }
                }                  //paths
                leaf unicast {
                    type enumeration {
                        enum unicast;
                    }
                }                  //unicast
                leaf unicast_community-list {
                    type enumeration {
                        enum unicast_community-list;
                    }
                }                  //community-list
                leaf unicast_filter-list {
                    type enumeration {
                        enum unicast_filter-list;
                    }
                }                  //filter-list
                leaf unicast_prefix-list {
                    type enumeration {
                        enum unicast_prefix-list;
                    }
                }                  //prefix-list
                leaf unicast_access-list {
                    type enumeration {
                        enum unicast_access-list;
                    }
                }                  //access-list
                leaf unicast_route-map {
                    type enumeration {
                        enum unicast_route-map;
                    }
                }                  //route-map
                leaf unicast_rpki {
                    type enumeration {
                        enum unicast_rpki;
                    }
                }                  //rpki
                leaf unicast_version {
                    type enumeration {
                        enum unicast_version;
                    }
                }                  //version
                leaf unicast_alias {
                    type enumeration {
                        enum unicast_alias;
                    }
                }                  //alias
                leaf unicast_wide {
                    type enumeration {
                        enum unicast_wide;
                    }
                }                  //wide
                leaf unicast_large-community-list {
                    type enumeration {
                        enum unicast_large-community-list;
                    }
                }                  //large-community-list
                leaf unicast_regexp {
                    type enumeration {
                        enum unicast_regexp;
                    }
                }                  //regexp
                leaf vpn_rd {
                    type enumeration {
                        enum vpn_rd;
                    }
                }                  //rd
                leaf unicast_all {
                    type enumeration {
                        enum unicast_all;
                    }
                }                  //unicast_all
                leaf unicast_all_community-list {
                    type enumeration {
                        enum unicast_all_community-list;
                    }
                }                  //community-list
                leaf unicast_all_filter-list {
                    type enumeration {
                        enum unicast_all_filter-list;
                    }
                }                  //filter-list
                leaf unicast_all_prefix-list {
                    type enumeration {
                        enum unicast_all_prefix-list;
                    }
                }                  //prefix-list
                leaf unicast_all_access-list {
                    type enumeration {
                        enum unicast_all_access-list;
                    }
                }                  //access-list
                leaf unicast_all_route-map {
                    type enumeration {
                        enum unicast_all_route-map;
                    }
                }                  //route-map
                leaf unicast_all_rpki {
                    type enumeration {
                        enum unicast_all_rpki;
                    }
                }                  //rpki
                leaf unicast_all_version {
                    type enumeration {
                        enum unicast_all_version;
                    }
                }                  //version
                leaf unicast_all_alias {
                    type enumeration {
                        enum unicast_all_alias;
                    }
                }                  //alias
                leaf unicast_all_wide {
                    type enumeration {
                        enum unicast_all_wide;
                    }
                }                  //wide
                leaf unicast_all_neighbors {
                    type enumeration {
                        enum unicast_all_neighbors;
                    }
                }                  //neighbors
                leaf unicast_cidr-only {
                    type enumeration {
                        enum unicast_cidr-only;
                    }
                }                  //unicast_cidr-only
                leaf unicast_cidr-only_wide {
                    type enumeration {
                        enum unicast_cidr-only_wide;
                    }
                }                  //wide
                leaf unicast_dampening {
                    type enumeration {
                        enum unicast_dampening;
                    }
                }                  //unicast_dampening
                leaf unicast_community {
                    type enumeration {
                        enum unicast_community;
                    }
                }                  //unicast_community
                leaf unicast_community_wide {
                    type enumeration {
                        enum unicast_community_wide;
                    }
                }                  //wide
                leaf unicast_detail-routes {
                    type enumeration {
                        enum unicast_detail-routes;
                    }
                }                  //unicast_detail-routes
                leaf unicast_detail-routes_wide {
                    type enumeration {
                        enum unicast_detail-routes_wide;
                    }
                }                  //wide
                leaf unicast_json {
                    type enumeration {
                        enum unicast_json;
                    }
                }                  //unicast_json
                leaf unicast_json_detail {
                    type enumeration {
                        enum unicast_json_detail;
                    }
                }                  //detail
                leaf unicast_summary {
                    type enumeration {
                        enum unicast_summary;
                    }
                }                  //unicast_summary
                leaf unicast_summary_neighbor {
                    type enumeration {
                        enum unicast_summary_neighbor;
                    }
                }                  //neighbor
                leaf unicast_summary_remote-as {
                    type enumeration {
                        enum unicast_summary_remote-as;
                    }
                }                  //remote-as
                leaf unicast_summary_json {
                    type enumeration {
                        enum unicast_summary_json;
                    }
                }                  //json
                leaf unicast_large-community {
                    type enumeration {
                        enum unicast_large-community;
                    }
                }                  //unicast_large-community
                leaf unicast_large-community_json {
                    type enumeration {
                        enum unicast_large-community_json;
                    }
                }                  //json
                leaf unicast_statistics {
                    type enumeration {
                        enum unicast_statistics;
                    }
                }                  //unicast_statistics
                leaf unicast_statistics_json {
                    type enumeration {
                        enum unicast_statistics_json;
                    }
                }                  //json
                leaf unicast_update-groups_json {
                    type enumeration {
                        enum unicast_update-groups_json;
                    }
                }                  //json
                leaf vpn_update-groups {
                    type enumeration {
                        enum vpn_update-groups;
                    }
                }                  //vpn_update-groups
                leaf vpn_route-leak {
                    type enumeration {
                        enum vpn_route-leak;
                    }
                }                  //vpn_route-leak
                leaf vpn_route-leak_json {
                    type enumeration {
                        enum vpn_route-leak_json;
                    }
                }                  //json
                leaf multicast_update-groups {
                    type enumeration {
                        enum multicast_update-groups;
                    }
                }                  //multicast_update-groups
                leaf multicast_route-leak {
                    type enumeration {
                        enum multicast_route-leak;
                    }
                }                  //multicast_route-leak
                leaf multicast_route-leak_json {
                    type enumeration {
                        enum multicast_route-leak_json;
                    }
                }                  //json
                leaf unicast_all_cidr-only {
                    type enumeration {
                        enum unicast_all_cidr-only;
                    }
                }                  //unicast_all_cidr-only
                leaf unicast_all_cidr-only_wide {
                    type enumeration {
                        enum unicast_all_cidr-only_wide;
                    }
                }                  //wide
                leaf unicast_all_dampening {
                    type enumeration {
                        enum unicast_all_dampening;
                    }
                }                  //unicast_all_dampening
                leaf unicast_all_community {
                    type enumeration {
                        enum unicast_all_community;
                    }
                }                  //unicast_all_community
                leaf unicast_all_community_wide {
                    type enumeration {
                        enum unicast_all_community_wide;
                    }
                }                  //wide
                leaf unicast_all_detail-routes {
                    type enumeration {
                        enum unicast_all_detail-routes;
                    }
                }                  //unicast_all_detail-routes
                leaf unicast_all_detail-routes_wide {
                    type enumeration {
                        enum unicast_all_detail-routes_wide;
                    }
                }                  //wide
                leaf unicast_all_json {
                    type enumeration {
                        enum unicast_all_json;
                    }
                }                  //unicast_all_json
                leaf unicast_all_json_detail {
                    type enumeration {
                        enum unicast_all_json_detail;
                    }
                }                  //detail
                leaf unicast_all_summary {
                    type enumeration {
                        enum unicast_all_summary;
                    }
                }                  //unicast_all_summary
                leaf unicast_all_summary_neighbor {
                    type enumeration {
                        enum unicast_all_summary_neighbor;
                    }
                }                  //neighbor
                leaf unicast_all_summary_remote-as {
                    type enumeration {
                        enum unicast_all_summary_remote-as;
                    }
                }                  //remote-as
                leaf unicast_all_summary_json {
                    type enumeration {
                        enum unicast_all_summary_json;
                    }
                }                  //json
                leaf unicast_cidr-only_json {
                    type enumeration {
                        enum unicast_cidr-only_json;
                    }
                }                  //unicast_cidr-only_json
                leaf unicast_cidr-only_json_detail {
                    type enumeration {
                        enum unicast_cidr-only_json_detail;
                    }
                }                  //detail
                leaf unicast_dampening_parameters {
                    type enumeration {
                        enum unicast_dampening_parameters;
                    }
                }                  //unicast_dampening_parameters
                leaf unicast_dampening_parameters_json {
                    type enumeration {
                        enum unicast_dampening_parameters_json;
                    }
                }                  //json
                leaf unicast_community_local-AS {
                    type enumeration {
                        enum unicast_community_local-AS;
                    }
                }                  //unicast_community_local-AS
                leaf unicast_community_local-AS_wide {
                    type enumeration {
                        enum unicast_community_local-AS_wide;
                    }
                }                  //wide
                leaf unicast_community_no-advertise {
                    type enumeration {
                        enum unicast_community_no-advertise;
                    }
                }                  //unicast_community_no-advertise
                leaf unicast_community_no-advertise_wide {
                    type enumeration {
                        enum unicast_community_no-advertise_wide;
                    }
                }                  //wide
                leaf unicast_community_no-export {
                    type enumeration {
                        enum unicast_community_no-export;
                    }
                }                  //unicast_community_no-export
                leaf unicast_community_no-export_wide {
                    type enumeration {
                        enum unicast_community_no-export_wide;
                    }
                }                  //wide
                leaf unicast_community_graceful-shutdown {
                    type enumeration {
                        enum unicast_community_graceful-shutdown;
                    }
                }                  //unicast_community_graceful-shutdown
                leaf unicast_community_graceful-shutdown_wide {
                    type enumeration {
                        enum unicast_community_graceful-shutdown_wide;
                    }
                }                  //wide
                leaf unicast_community_no-peer {
                    type enumeration {
                        enum unicast_community_no-peer;
                    }
                }                  //unicast_community_no-peer
                leaf unicast_community_no-peer_wide {
                    type enumeration {
                        enum unicast_community_no-peer_wide;
                    }
                }                  //wide
                leaf unicast_community_blackhole {
                    type enumeration {
                        enum unicast_community_blackhole;
                    }
                }                  //unicast_community_blackhole
                leaf unicast_community_blackhole_wide {
                    type enumeration {
                        enum unicast_community_blackhole_wide;
                    }
                }                  //wide
                leaf unicast_community_llgr-stale {
                    type enumeration {
                        enum unicast_community_llgr-stale;
                    }
                }                  //unicast_community_llgr-stale
                leaf unicast_community_llgr-stale_wide {
                    type enumeration {
                        enum unicast_community_llgr-stale_wide;
                    }
                }                  //wide
                leaf unicast_community_no-llgr {
                    type enumeration {
                        enum unicast_community_no-llgr;
                    }
                }                  //unicast_community_no-llgr
                leaf unicast_community_no-llgr_wide {
                    type enumeration {
                        enum unicast_community_no-llgr_wide;
                    }
                }                  //wide
                leaf unicast_community_accept-own {
                    type enumeration {
                        enum unicast_community_accept-own;
                    }
                }                  //unicast_community_accept-own
                leaf unicast_community_accept-own_wide {
                    type enumeration {
                        enum unicast_community_accept-own_wide;
                    }
                }                  //wide
                leaf unicast_community_accept-own-nexthop {
                    type enumeration {
                        enum unicast_community_accept-own-nexthop;
                    }
                }                  //unicast_community_accept-own-nexthop
                leaf unicast_community_accept-own-nexthop_wide {
                    type enumeration {
                        enum unicast_community_accept-own-nexthop_wide;
                    }
                }                  //wide
                leaf unicast_community_route-filter-v6 {
                    type enumeration {
                        enum unicast_community_route-filter-v6;
                    }
                }                  //unicast_community_route-filter-v6
                leaf unicast_community_route-filter-v6_wide {
                    type enumeration {
                        enum unicast_community_route-filter-v6_wide;
                    }
                }                  //wide
                leaf unicast_community_route-filter-v4 {
                    type enumeration {
                        enum unicast_community_route-filter-v4;
                    }
                }                  //unicast_community_route-filter-v4
                leaf unicast_community_route-filter-v4_wide {
                    type enumeration {
                        enum unicast_community_route-filter-v4_wide;
                    }
                }                  //wide
                leaf unicast_community_route-filter-translated-v6 {
                    type enumeration {
                        enum unicast_community_route-filter-translated-v6;
                    }
                }                  //unicast_community_route-filter-translated-v6
                leaf unicast_community_route-filter-translated-v6_wide {
                    type enumeration {
                        enum unicast_community_route-filter-translated-v6_wide;
                    }
                }                  //wide
                leaf unicast_community_route-filter-translated-v4 {
                    type enumeration {
                        enum unicast_community_route-filter-translated-v4;
                    }
                }                  //unicast_community_route-filter-translated-v4
                leaf unicast_community_route-filter-translated-v4_wide {
                    type enumeration {
                        enum unicast_community_route-filter-translated-v4_wide;
                    }
                }                  //wide
                leaf unicast_community_exact-match {
                    type enumeration {
                        enum unicast_community_exact-match;
                    }
                }                  //unicast_community_exact-match
                leaf unicast_community_exact-match_wide {
                    type enumeration {
                        enum unicast_community_exact-match_wide;
                    }
                }                  //wide
                leaf unicast_community_json {
                    type enumeration {
                        enum unicast_community_json;
                    }
                }                  //unicast_community_json
                leaf unicast_community_json_detail {
                    type enumeration {
                        enum unicast_community_json_detail;
                    }
                }                  //detail
                leaf unicast_detail-routes_json {
                    type enumeration {
                        enum unicast_detail-routes_json;
                    }
                }                  //unicast_detail-routes_json
                leaf unicast_detail-routes_json_detail {
                    type enumeration {
                        enum unicast_detail-routes_json_detail;
                    }
                }                  //detail
                leaf unicast_summary_established {
                    type enumeration {
                        enum unicast_summary_established;
                    }
                }                  //unicast_summary_established
                leaf unicast_summary_established_neighbor {
                    type enumeration {
                        enum unicast_summary_established_neighbor;
                    }
                }                  //neighbor
                leaf unicast_summary_established_remote-as {
                    type enumeration {
                        enum unicast_summary_established_remote-as;
                    }
                }                  //remote-as
                leaf unicast_summary_established_json {
                    type enumeration {
                        enum unicast_summary_established_json;
                    }
                }                  //json
                leaf unicast_summary_failed {
                    type enumeration {
                        enum unicast_summary_failed;
                    }
                }                  //unicast_summary_failed
                leaf unicast_summary_failed_neighbor {
                    type enumeration {
                        enum unicast_summary_failed_neighbor;
                    }
                }                  //neighbor
                leaf unicast_summary_failed_remote-as {
                    type enumeration {
                        enum unicast_summary_failed_remote-as;
                    }
                }                  //remote-as
                leaf unicast_summary_failed_json {
                    type enumeration {
                        enum unicast_summary_failed_json;
                    }
                }                  //json
                leaf unicast_summary_terse {
                    type enumeration {
                        enum unicast_summary_terse;
                    }
                }                  //unicast_summary_terse
                leaf unicast_summary_terse_json {
                    type enumeration {
                        enum unicast_summary_terse_json;
                    }
                }                  //json
                leaf unicast_summary_wide {
                    type enumeration {
                        enum unicast_summary_wide;
                    }
                }                  //unicast_summary_wide
                leaf unicast_summary_wide_json {
                    type enumeration {
                        enum unicast_summary_wide_json;
                    }
                }                  //json
                leaf unicast_all_cidr-only_json {
                    type enumeration {
                        enum unicast_all_cidr-only_json;
                    }
                }                  //unicast_all_cidr-only_json
                leaf unicast_all_cidr-only_json_detail {
                    type enumeration {
                        enum unicast_all_cidr-only_json_detail;
                    }
                }                  //detail
                leaf unicast_all_dampening_parameters {
                    type enumeration {
                        enum unicast_all_dampening_parameters;
                    }
                }                  //unicast_all_dampening_parameters
                leaf unicast_all_dampening_parameters_json {
                    type enumeration {
                        enum unicast_all_dampening_parameters_json;
                    }
                }                  //json
                leaf unicast_all_community_local-AS {
                    type enumeration {
                        enum unicast_all_community_local-AS;
                    }
                }                  //unicast_all_community_local-AS
                leaf unicast_all_community_local-AS_wide {
                    type enumeration {
                        enum unicast_all_community_local-AS_wide;
                    }
                }                  //wide
                leaf unicast_all_community_no-advertise {
                    type enumeration {
                        enum unicast_all_community_no-advertise;
                    }
                }                  //unicast_all_community_no-advertise
                leaf unicast_all_community_no-advertise_wide {
                    type enumeration {
                        enum unicast_all_community_no-advertise_wide;
                    }
                }                  //wide
                leaf unicast_all_community_no-export {
                    type enumeration {
                        enum unicast_all_community_no-export;
                    }
                }                  //unicast_all_community_no-export
                leaf unicast_all_community_no-export_wide {
                    type enumeration {
                        enum unicast_all_community_no-export_wide;
                    }
                }                  //wide
                leaf unicast_all_community_graceful-shutdown {
                    type enumeration {
                        enum unicast_all_community_graceful-shutdown;
                    }
                }                  //unicast_all_community_graceful-shutdown
                leaf unicast_all_community_graceful-shutdown_wide {
                    type enumeration {
                        enum unicast_all_community_graceful-shutdown_wide;
                    }
                }                  //wide
                leaf unicast_all_community_no-peer {
                    type enumeration {
                        enum unicast_all_community_no-peer;
                    }
                }                  //unicast_all_community_no-peer
                leaf unicast_all_community_no-peer_wide {
                    type enumeration {
                        enum unicast_all_community_no-peer_wide;
                    }
                }                  //wide
                leaf unicast_all_community_blackhole {
                    type enumeration {
                        enum unicast_all_community_blackhole;
                    }
                }                  //unicast_all_community_blackhole
                leaf unicast_all_community_blackhole_wide {
                    type enumeration {
                        enum unicast_all_community_blackhole_wide;
                    }
                }                  //wide
                leaf unicast_all_community_llgr-stale {
                    type enumeration {
                        enum unicast_all_community_llgr-stale;
                    }
                }                  //unicast_all_community_llgr-stale
                leaf unicast_all_community_llgr-stale_wide {
                    type enumeration {
                        enum unicast_all_community_llgr-stale_wide;
                    }
                }                  //wide
                leaf unicast_all_community_no-llgr {
                    type enumeration {
                        enum unicast_all_community_no-llgr;
                    }
                }                  //unicast_all_community_no-llgr
                leaf unicast_all_community_no-llgr_wide {
                    type enumeration {
                        enum unicast_all_community_no-llgr_wide;
                    }
                }                  //wide
                leaf unicast_all_community_accept-own {
                    type enumeration {
                        enum unicast_all_community_accept-own;
                    }
                }                  //unicast_all_community_accept-own
                leaf unicast_all_community_accept-own_wide {
                    type enumeration {
                        enum unicast_all_community_accept-own_wide;
                    }
                }                  //wide
                leaf unicast_all_community_accept-own-nexthop {
                    type enumeration {
                        enum unicast_all_community_accept-own-nexthop;
                    }
                }                  //unicast_all_community_accept-own-nexthop
                leaf unicast_all_community_accept-own-nexthop_wide {
                    type enumeration {
                        enum unicast_all_community_accept-own-nexthop_wide;
                    }
                }                  //wide
                leaf unicast_all_community_route-filter-v6 {
                    type enumeration {
                        enum unicast_all_community_route-filter-v6;
                    }
                }                  //unicast_all_community_route-filter-v6
                leaf unicast_all_community_route-filter-v6_wide {
                    type enumeration {
                        enum unicast_all_community_route-filter-v6_wide;
                    }
                }                  //wide
                leaf unicast_all_community_route-filter-v4 {
                    type enumeration {
                        enum unicast_all_community_route-filter-v4;
                    }
                }                  //unicast_all_community_route-filter-v4
                leaf unicast_all_community_route-filter-v4_wide {
                    type enumeration {
                        enum unicast_all_community_route-filter-v4_wide;
                    }
                }                  //wide
                leaf unicast_all_community_route-filter-translated-v6 {
                    type enumeration {
                        enum unicast_all_community_route-filter-translated-v6;
                    }
                }                  //unicast_all_community_route-filter-translated-v6
                leaf unicast_all_community_route-filter-translated-v6_wide {
                    type enumeration {
                        enum unicast_all_community_route-filter-translated-v6_wide;
                    }
                }                  //wide
                leaf unicast_all_community_route-filter-translated-v4 {
                    type enumeration {
                        enum unicast_all_community_route-filter-translated-v4;
                    }
                }                  //unicast_all_community_route-filter-translated-v4
                leaf unicast_all_community_route-filter-translated-v4_wide {
                    type enumeration {
                        enum unicast_all_community_route-filter-translated-v4_wide;
                    }
                }                  //wide
                leaf unicast_all_community_exact-match {
                    type enumeration {
                        enum unicast_all_community_exact-match;
                    }
                }                  //unicast_all_community_exact-match
                leaf unicast_all_community_exact-match_wide {
                    type enumeration {
                        enum unicast_all_community_exact-match_wide;
                    }
                }                  //wide
                leaf unicast_all_community_json {
                    type enumeration {
                        enum unicast_all_community_json;
                    }
                }                  //unicast_all_community_json
                leaf unicast_all_community_json_detail {
                    type enumeration {
                        enum unicast_all_community_json_detail;
                    }
                }                  //detail
                leaf unicast_all_detail-routes_json {
                    type enumeration {
                        enum unicast_all_detail-routes_json;
                    }
                }                  //unicast_all_detail-routes_json
                leaf unicast_all_detail-routes_json_detail {
                    type enumeration {
                        enum unicast_all_detail-routes_json_detail;
                    }
                }                  //detail
                leaf unicast_all_summary_established {
                    type enumeration {
                        enum unicast_all_summary_established;
                    }
                }                  //unicast_all_summary_established
                leaf unicast_all_summary_established_neighbor {
                    type enumeration {
                        enum unicast_all_summary_established_neighbor;
                    }
                }                  //neighbor
                leaf unicast_all_summary_established_remote-as {
                    type enumeration {
                        enum unicast_all_summary_established_remote-as;
                    }
                }                  //remote-as
                leaf unicast_all_summary_established_json {
                    type enumeration {
                        enum unicast_all_summary_established_json;
                    }
                }                  //json
                leaf unicast_all_summary_failed {
                    type enumeration {
                        enum unicast_all_summary_failed;
                    }
                }                  //unicast_all_summary_failed
                leaf unicast_all_summary_failed_neighbor {
                    type enumeration {
                        enum unicast_all_summary_failed_neighbor;
                    }
                }                  //neighbor
                leaf unicast_all_summary_failed_remote-as {
                    type enumeration {
                        enum unicast_all_summary_failed_remote-as;
                    }
                }                  //remote-as
                leaf unicast_all_summary_failed_json {
                    type enumeration {
                        enum unicast_all_summary_failed_json;
                    }
                }                  //json
                leaf unicast_all_summary_terse {
                    type enumeration {
                        enum unicast_all_summary_terse;
                    }
                }                  //unicast_all_summary_terse
                leaf unicast_all_summary_terse_json {
                    type enumeration {
                        enum unicast_all_summary_terse_json;
                    }
                }                  //json
                leaf unicast_all_summary_wide {
                    type enumeration {
                        enum unicast_all_summary_wide;
                    }
                }                  //unicast_all_summary_wide
                leaf unicast_all_summary_wide_json {
                    type enumeration {
                        enum unicast_all_summary_wide_json;
                    }
                }                  //json
                leaf unicast_community_local-AS_exact-match {
                    type enumeration {
                        enum unicast_community_local-AS_exact-match;
                    }
                }                  //unicast_community_local-AS_exact-match
                leaf unicast_community_local-AS_exact-match_wide {
                    type enumeration {
                        enum unicast_community_local-AS_exact-match_wide;
                    }
                }                  //wide
                leaf unicast_community_local-AS_json {
                    type enumeration {
                        enum unicast_community_local-AS_json;
                    }
                }                  //unicast_community_local-AS_json
                leaf unicast_community_local-AS_json_detail {
                    type enumeration {
                        enum unicast_community_local-AS_json_detail;
                    }
                }                  //detail
                leaf unicast_community_no-advertise_exact-match {
                    type enumeration {
                        enum unicast_community_no-advertise_exact-match;
                    }
                }                  //unicast_community_no-advertise_exact-match
                leaf unicast_community_no-advertise_exact-match_wide {
                    type enumeration {
                        enum unicast_community_no-advertise_exact-match_wide;
                    }
                }                  //wide
                leaf unicast_community_no-advertise_json {
                    type enumeration {
                        enum unicast_community_no-advertise_json;
                    }
                }                  //unicast_community_no-advertise_json
                leaf unicast_community_no-advertise_json_detail {
                    type enumeration {
                        enum unicast_community_no-advertise_json_detail;
                    }
                }                  //detail
                leaf unicast_community_no-export_exact-match {
                    type enumeration {
                        enum unicast_community_no-export_exact-match;
                    }
                }                  //unicast_community_no-export_exact-match
                leaf unicast_community_no-export_exact-match_wide {
                    type enumeration {
                        enum unicast_community_no-export_exact-match_wide;
                    }
                }                  //wide
                leaf unicast_community_no-export_json {
                    type enumeration {
                        enum unicast_community_no-export_json;
                    }
                }                  //unicast_community_no-export_json
                leaf unicast_community_no-export_json_detail {
                    type enumeration {
                        enum unicast_community_no-export_json_detail;
                    }
                }                  //detail
                leaf unicast_community_graceful-shutdown_exact-match {
                    type enumeration {
                        enum unicast_community_graceful-shutdown_exact-match;
                    }
                }                  //unicast_community_graceful-shutdown_exact-match
                leaf unicast_community_graceful-shutdown_exact-match_wide {
                    type enumeration {
                        enum unicast_community_graceful-shutdown_exact-match_wide;
                    }
                }                  //wide
                leaf unicast_community_graceful-shutdown_json {
                    type enumeration {
                        enum unicast_community_graceful-shutdown_json;
                    }
                }                  //unicast_community_graceful-shutdown_json
                leaf unicast_community_graceful-shutdown_json_detail {
                    type enumeration {
                        enum unicast_community_graceful-shutdown_json_detail;
                    }
                }                  //detail
                leaf unicast_community_no-peer_exact-match {
                    type enumeration {
                        enum unicast_community_no-peer_exact-match;
                    }
                }                  //unicast_community_no-peer_exact-match
                leaf unicast_community_no-peer_exact-match_wide {
                    type enumeration {
                        enum unicast_community_no-peer_exact-match_wide;
                    }
                }                  //wide
                leaf unicast_community_no-peer_json {
                    type enumeration {
                        enum unicast_community_no-peer_json;
                    }
                }                  //unicast_community_no-peer_json
                leaf unicast_community_no-peer_json_detail {
                    type enumeration {
                        enum unicast_community_no-peer_json_detail;
                    }
                }                  //detail
                leaf unicast_community_blackhole_exact-match {
                    type enumeration {
                        enum unicast_community_blackhole_exact-match;
                    }
                }                  //unicast_community_blackhole_exact-match
                leaf unicast_community_blackhole_exact-match_wide {
                    type enumeration {
                        enum unicast_community_blackhole_exact-match_wide;
                    }
                }                  //wide
                leaf unicast_community_blackhole_json {
                    type enumeration {
                        enum unicast_community_blackhole_json;
                    }
                }                  //unicast_community_blackhole_json
                leaf unicast_community_blackhole_json_detail {
                    type enumeration {
                        enum unicast_community_blackhole_json_detail;
                    }
                }                  //detail
                leaf unicast_community_llgr-stale_exact-match {
                    type enumeration {
                        enum unicast_community_llgr-stale_exact-match;
                    }
                }                  //unicast_community_llgr-stale_exact-match
                leaf unicast_community_llgr-stale_exact-match_wide {
                    type enumeration {
                        enum unicast_community_llgr-stale_exact-match_wide;
                    }
                }                  //wide
                leaf unicast_community_llgr-stale_json {
                    type enumeration {
                        enum unicast_community_llgr-stale_json;
                    }
                }                  //unicast_community_llgr-stale_json
                leaf unicast_community_llgr-stale_json_detail {
                    type enumeration {
                        enum unicast_community_llgr-stale_json_detail;
                    }
                }                  //detail
                leaf unicast_community_no-llgr_exact-match {
                    type enumeration {
                        enum unicast_community_no-llgr_exact-match;
                    }
                }                  //unicast_community_no-llgr_exact-match
                leaf unicast_community_no-llgr_exact-match_wide {
                    type enumeration {
                        enum unicast_community_no-llgr_exact-match_wide;
                    }
                }                  //wide
                leaf unicast_community_no-llgr_json {
                    type enumeration {
                        enum unicast_community_no-llgr_json;
                    }
                }                  //unicast_community_no-llgr_json
                leaf unicast_community_no-llgr_json_detail {
                    type enumeration {
                        enum unicast_community_no-llgr_json_detail;
                    }
                }                  //detail
                leaf unicast_community_accept-own_exact-match {
                    type enumeration {
                        enum unicast_community_accept-own_exact-match;
                    }
                }                  //unicast_community_accept-own_exact-match
                leaf unicast_community_accept-own_exact-match_wide {
                    type enumeration {
                        enum unicast_community_accept-own_exact-match_wide;
                    }
                }                  //wide
                leaf unicast_community_accept-own_json {
                    type enumeration {
                        enum unicast_community_accept-own_json;
                    }
                }                  //unicast_community_accept-own_json
                leaf unicast_community_accept-own_json_detail {
                    type enumeration {
                        enum unicast_community_accept-own_json_detail;
                    }
                }                  //detail
                leaf unicast_community_accept-own-nexthop_exact-match {
                    type enumeration {
                        enum unicast_community_accept-own-nexthop_exact-match;
                    }
                }                  //unicast_community_accept-own-nexthop_exact-match
                leaf unicast_community_accept-own-nexthop_exact-match_wide {
                    type enumeration {
                        enum unicast_community_accept-own-nexthop_exact-match_wide;
                    }
                }                  //wide
                leaf unicast_community_accept-own-nexthop_json {
                    type enumeration {
                        enum unicast_community_accept-own-nexthop_json;
                    }
                }                  //unicast_community_accept-own-nexthop_json
                leaf unicast_community_accept-own-nexthop_json_detail {
                    type enumeration {
                        enum unicast_community_accept-own-nexthop_json_detail;
                    }
                }                  //detail
                leaf unicast_community_route-filter-v6_exact-match {
                    type enumeration {
                        enum unicast_community_route-filter-v6_exact-match;
                    }
                }                  //unicast_community_route-filter-v6_exact-match
                leaf unicast_community_route-filter-v6_exact-match_wide {
                    type enumeration {
                        enum unicast_community_route-filter-v6_exact-match_wide;
                    }
                }                  //wide
                leaf unicast_community_route-filter-v6_json {
                    type enumeration {
                        enum unicast_community_route-filter-v6_json;
                    }
                }                  //unicast_community_route-filter-v6_json
                leaf unicast_community_route-filter-v6_json_detail {
                    type enumeration {
                        enum unicast_community_route-filter-v6_json_detail;
                    }
                }                  //detail
                leaf unicast_community_route-filter-v4_exact-match {
                    type enumeration {
                        enum unicast_community_route-filter-v4_exact-match;
                    }
                }                  //unicast_community_route-filter-v4_exact-match
                leaf unicast_community_route-filter-v4_exact-match_wide {
                    type enumeration {
                        enum unicast_community_route-filter-v4_exact-match_wide;
                    }
                }                  //wide
                leaf unicast_community_route-filter-v4_json {
                    type enumeration {
                        enum unicast_community_route-filter-v4_json;
                    }
                }                  //unicast_community_route-filter-v4_json
                leaf unicast_community_route-filter-v4_json_detail {
                    type enumeration {
                        enum unicast_community_route-filter-v4_json_detail;
                    }
                }                  //detail
                leaf unicast_community_route-filter-translated-v6_exact-match {
                    type enumeration {
                        enum unicast_community_route-filter-translated-v6_exact-match;
                    }
                }                  //unicast_community_route-filter-translated-v6_exact-match
                leaf unicast_community_route-filter-translated-v6_exact-match_wide {
                    type enumeration {
                        enum unicast_community_route-filter-translated-v6_exact-match_wide;
                    }
                }                  //wide
                leaf unicast_community_route-filter-translated-v6_json {
                    type enumeration {
                        enum unicast_community_route-filter-translated-v6_json;
                    }
                }                  //unicast_community_route-filter-translated-v6_json
                leaf unicast_community_route-filter-translated-v6_json_detail {
                    type enumeration {
                        enum unicast_community_route-filter-translated-v6_json_detail;
                    }
                }                  //detail
                leaf unicast_community_route-filter-translated-v4_exact-match {
                    type enumeration {
                        enum unicast_community_route-filter-translated-v4_exact-match;
                    }
                }                  //unicast_community_route-filter-translated-v4_exact-match
                leaf unicast_community_route-filter-translated-v4_exact-match_wide {
                    type enumeration {
                        enum unicast_community_route-filter-translated-v4_exact-match_wide;
                    }
                }                  //wide
                leaf unicast_community_route-filter-translated-v4_json {
                    type enumeration {
                        enum unicast_community_route-filter-translated-v4_json;
                    }
                }                  //unicast_community_route-filter-translated-v4_json
                leaf unicast_community_route-filter-translated-v4_json_detail {
                    type enumeration {
                        enum unicast_community_route-filter-translated-v4_json_detail;
                    }
                }                  //detail
                leaf unicast_community_exact-match_json {
                    type enumeration {
                        enum unicast_community_exact-match_json;
                    }
                }                  //unicast_community_exact-match_json
                leaf unicast_community_exact-match_json_detail {
                    type enumeration {
                        enum unicast_community_exact-match_json_detail;
                    }
                }                  //detail
                leaf unicast_summary_established_terse {
                    type enumeration {
                        enum unicast_summary_established_terse;
                    }
                }                  //unicast_summary_established_terse
                leaf unicast_summary_established_terse_json {
                    type enumeration {
                        enum unicast_summary_established_terse_json;
                    }
                }                  //json
                leaf unicast_summary_established_wide {
                    type enumeration {
                        enum unicast_summary_established_wide;
                    }
                }                  //unicast_summary_established_wide
                leaf unicast_summary_established_wide_json {
                    type enumeration {
                        enum unicast_summary_established_wide_json;
                    }
                }                  //json
                leaf unicast_summary_failed_terse {
                    type enumeration {
                        enum unicast_summary_failed_terse;
                    }
                }                  //unicast_summary_failed_terse
                leaf unicast_summary_failed_terse_json {
                    type enumeration {
                        enum unicast_summary_failed_terse_json;
                    }
                }                  //json
                leaf unicast_summary_failed_wide {
                    type enumeration {
                        enum unicast_summary_failed_wide;
                    }
                }                  //unicast_summary_failed_wide
                leaf unicast_summary_failed_wide_json {
                    type enumeration {
                        enum unicast_summary_failed_wide_json;
                    }
                }                  //json
                leaf unicast_summary_terse_wide {
                    type enumeration {
                        enum unicast_summary_terse_wide;
                    }
                }                  //unicast_summary_terse_wide
                leaf unicast_summary_terse_wide_json {
                    type enumeration {
                        enum unicast_summary_terse_wide_json;
                    }
                }                  //json
                leaf unicast_all_community_local-AS_exact-match {
                    type enumeration {
                        enum unicast_all_community_local-AS_exact-match;
                    }
                }                  //unicast_all_community_local-AS_exact-match
                leaf unicast_all_community_local-AS_exact-match_wide {
                    type enumeration {
                        enum unicast_all_community_local-AS_exact-match_wide;
                    }
                }                  //wide
                leaf unicast_all_community_local-AS_json {
                    type enumeration {
                        enum unicast_all_community_local-AS_json;
                    }
                }                  //unicast_all_community_local-AS_json
                leaf unicast_all_community_local-AS_json_detail {
                    type enumeration {
                        enum unicast_all_community_local-AS_json_detail;
                    }
                }                  //detail
                leaf unicast_all_community_no-advertise_exact-match {
                    type enumeration {
                        enum unicast_all_community_no-advertise_exact-match;
                    }
                }                  //unicast_all_community_no-advertise_exact-match
                leaf unicast_all_community_no-advertise_exact-match_wide {
                    type enumeration {
                        enum unicast_all_community_no-advertise_exact-match_wide;
                    }
                }                  //wide
                leaf unicast_all_community_no-advertise_json {
                    type enumeration {
                        enum unicast_all_community_no-advertise_json;
                    }
                }                  //unicast_all_community_no-advertise_json
                leaf unicast_all_community_no-advertise_json_detail {
                    type enumeration {
                        enum unicast_all_community_no-advertise_json_detail;
                    }
                }                  //detail
                leaf unicast_all_community_no-export_exact-match {
                    type enumeration {
                        enum unicast_all_community_no-export_exact-match;
                    }
                }                  //unicast_all_community_no-export_exact-match
                leaf unicast_all_community_no-export_exact-match_wide {
                    type enumeration {
                        enum unicast_all_community_no-export_exact-match_wide;
                    }
                }                  //wide
                leaf unicast_all_community_no-export_json {
                    type enumeration {
                        enum unicast_all_community_no-export_json;
                    }
                }                  //unicast_all_community_no-export_json
                leaf unicast_all_community_no-export_json_detail {
                    type enumeration {
                        enum unicast_all_community_no-export_json_detail;
                    }
                }                  //detail
                leaf unicast_all_community_graceful-shutdown_exact-match {
                    type enumeration {
                        enum unicast_all_community_graceful-shutdown_exact-match;
                    }
                }                  //unicast_all_community_graceful-shutdown_exact-match
                leaf unicast_all_community_graceful-shutdown_exact-match_wide {
                    type enumeration {
                        enum unicast_all_community_graceful-shutdown_exact-match_wide;
                    }
                }                  //wide
                leaf unicast_all_community_graceful-shutdown_json {
                    type enumeration {
                        enum unicast_all_community_graceful-shutdown_json;
                    }
                }                  //unicast_all_community_graceful-shutdown_json
                leaf unicast_all_community_graceful-shutdown_json_detail {
                    type enumeration {
                        enum unicast_all_community_graceful-shutdown_json_detail;
                    }
                }                  //detail
                leaf unicast_all_community_no-peer_exact-match {
                    type enumeration {
                        enum unicast_all_community_no-peer_exact-match;
                    }
                }                  //unicast_all_community_no-peer_exact-match
                leaf unicast_all_community_no-peer_exact-match_wide {
                    type enumeration {
                        enum unicast_all_community_no-peer_exact-match_wide;
                    }
                }                  //wide
                leaf unicast_all_community_no-peer_json {
                    type enumeration {
                        enum unicast_all_community_no-peer_json;
                    }
                }                  //unicast_all_community_no-peer_json
                leaf unicast_all_community_no-peer_json_detail {
                    type enumeration {
                        enum unicast_all_community_no-peer_json_detail;
                    }
                }                  //detail
                leaf unicast_all_community_blackhole_exact-match {
                    type enumeration {
                        enum unicast_all_community_blackhole_exact-match;
                    }
                }                  //unicast_all_community_blackhole_exact-match
                leaf unicast_all_community_blackhole_exact-match_wide {
                    type enumeration {
                        enum unicast_all_community_blackhole_exact-match_wide;
                    }
                }                  //wide
                leaf unicast_all_community_blackhole_json {
                    type enumeration {
                        enum unicast_all_community_blackhole_json;
                    }
                }                  //unicast_all_community_blackhole_json
                leaf unicast_all_community_blackhole_json_detail {
                    type enumeration {
                        enum unicast_all_community_blackhole_json_detail;
                    }
                }                  //detail
                leaf unicast_all_community_llgr-stale_exact-match {
                    type enumeration {
                        enum unicast_all_community_llgr-stale_exact-match;
                    }
                }                  //unicast_all_community_llgr-stale_exact-match
                leaf unicast_all_community_llgr-stale_exact-match_wide {
                    type enumeration {
                        enum unicast_all_community_llgr-stale_exact-match_wide;
                    }
                }                  //wide
                leaf unicast_all_community_llgr-stale_json {
                    type enumeration {
                        enum unicast_all_community_llgr-stale_json;
                    }
                }                  //unicast_all_community_llgr-stale_json
                leaf unicast_all_community_llgr-stale_json_detail {
                    type enumeration {
                        enum unicast_all_community_llgr-stale_json_detail;
                    }
                }                  //detail
                leaf unicast_all_community_no-llgr_exact-match {
                    type enumeration {
                        enum unicast_all_community_no-llgr_exact-match;
                    }
                }                  //unicast_all_community_no-llgr_exact-match
                leaf unicast_all_community_no-llgr_exact-match_wide {
                    type enumeration {
                        enum unicast_all_community_no-llgr_exact-match_wide;
                    }
                }                  //wide
                leaf unicast_all_community_no-llgr_json {
                    type enumeration {
                        enum unicast_all_community_no-llgr_json;
                    }
                }                  //unicast_all_community_no-llgr_json
                leaf unicast_all_community_no-llgr_json_detail {
                    type enumeration {
                        enum unicast_all_community_no-llgr_json_detail;
                    }
                }                  //detail
                leaf unicast_all_community_accept-own_exact-match {
                    type enumeration {
                        enum unicast_all_community_accept-own_exact-match;
                    }
                }                  //unicast_all_community_accept-own_exact-match
                leaf unicast_all_community_accept-own_exact-match_wide {
                    type enumeration {
                        enum unicast_all_community_accept-own_exact-match_wide;
                    }
                }                  //wide
                leaf unicast_all_community_accept-own_json {
                    type enumeration {
                        enum unicast_all_community_accept-own_json;
                    }
                }                  //unicast_all_community_accept-own_json
                leaf unicast_all_community_accept-own_json_detail {
                    type enumeration {
                        enum unicast_all_community_accept-own_json_detail;
                    }
                }                  //detail
                leaf unicast_all_community_accept-own-nexthop_exact-match {
                    type enumeration {
                        enum unicast_all_community_accept-own-nexthop_exact-match;
                    }
                }                  //unicast_all_community_accept-own-nexthop_exact-match
                leaf unicast_all_community_accept-own-nexthop_exact-match_wide {
                    type enumeration {
                        enum unicast_all_community_accept-own-nexthop_exact-match_wide;
                    }
                }                  //wide
                leaf unicast_all_community_accept-own-nexthop_json {
                    type enumeration {
                        enum unicast_all_community_accept-own-nexthop_json;
                    }
                }                  //unicast_all_community_accept-own-nexthop_json
                leaf unicast_all_community_accept-own-nexthop_json_detail {
                    type enumeration {
                        enum unicast_all_community_accept-own-nexthop_json_detail;
                    }
                }                  //detail
                leaf unicast_all_community_route-filter-v6_exact-match {
                    type enumeration {
                        enum unicast_all_community_route-filter-v6_exact-match;
                    }
                }                  //unicast_all_community_route-filter-v6_exact-match
                leaf unicast_all_community_route-filter-v6_exact-match_wide {
                    type enumeration {
                        enum unicast_all_community_route-filter-v6_exact-match_wide;
                    }
                }                  //wide
                leaf unicast_all_community_route-filter-v6_json {
                    type enumeration {
                        enum unicast_all_community_route-filter-v6_json;
                    }
                }                  //unicast_all_community_route-filter-v6_json
                leaf unicast_all_community_route-filter-v6_json_detail {
                    type enumeration {
                        enum unicast_all_community_route-filter-v6_json_detail;
                    }
                }                  //detail
                leaf unicast_all_community_route-filter-v4_exact-match {
                    type enumeration {
                        enum unicast_all_community_route-filter-v4_exact-match;
                    }
                }                  //unicast_all_community_route-filter-v4_exact-match
                leaf unicast_all_community_route-filter-v4_exact-match_wide {
                    type enumeration {
                        enum unicast_all_community_route-filter-v4_exact-match_wide;
                    }
                }                  //wide
                leaf unicast_all_community_route-filter-v4_json {
                    type enumeration {
                        enum unicast_all_community_route-filter-v4_json;
                    }
                }                  //unicast_all_community_route-filter-v4_json
                leaf unicast_all_community_route-filter-v4_json_detail {
                    type enumeration {
                        enum unicast_all_community_route-filter-v4_json_detail;
                    }
                }                  //detail
                leaf unicast_all_community_route-filter-translated-v6_exact-match {
                    type enumeration {
                        enum unicast_all_community_route-filter-translated-v6_exact-match;
                    }
                }                  //unicast_all_community_route-filter-translated-v6_exact-match
                leaf unicast_all_community_route-filter-translated-v6_exact-match_wide {
                    type enumeration {
                        enum unicast_all_community_route-filter-translated-v6_exact-match_wide;
                    }
                }                  //wide
                leaf unicast_all_community_route-filter-translated-v6_json {
                    type enumeration {
                        enum unicast_all_community_route-filter-translated-v6_json;
                    }
                }                  //unicast_all_community_route-filter-translated-v6_json
                leaf unicast_all_community_route-filter-translated-v6_json_detail {
                    type enumeration {
                        enum unicast_all_community_route-filter-translated-v6_json_detail;
                    }
                }                  //detail
                leaf unicast_all_community_route-filter-translated-v4_exact-match {
                    type enumeration {
                        enum unicast_all_community_route-filter-translated-v4_exact-match;
                    }
                }                  //unicast_all_community_route-filter-translated-v4_exact-match
                leaf unicast_all_community_route-filter-translated-v4_exact-match_wide {
                    type enumeration {
                        enum unicast_all_community_route-filter-translated-v4_exact-match_wide;
                    }
                }                  //wide
                leaf unicast_all_community_route-filter-translated-v4_json {
                    type enumeration {
                        enum unicast_all_community_route-filter-translated-v4_json;
                    }
                }                  //unicast_all_community_route-filter-translated-v4_json
                leaf unicast_all_community_route-filter-translated-v4_json_detail {
                    type enumeration {
                        enum unicast_all_community_route-filter-translated-v4_json_detail;
                    }
                }                  //detail
                leaf unicast_all_community_exact-match_json {
                    type enumeration {
                        enum unicast_all_community_exact-match_json;
                    }
                }                  //unicast_all_community_exact-match_json
                leaf unicast_all_community_exact-match_json_detail {
                    type enumeration {
                        enum unicast_all_community_exact-match_json_detail;
                    }
                }                  //detail
                leaf unicast_all_summary_established_terse {
                    type enumeration {
                        enum unicast_all_summary_established_terse;
                    }
                }                  //unicast_all_summary_established_terse
                leaf unicast_all_summary_established_terse_json {
                    type enumeration {
                        enum unicast_all_summary_established_terse_json;
                    }
                }                  //json
                leaf unicast_all_summary_established_wide {
                    type enumeration {
                        enum unicast_all_summary_established_wide;
                    }
                }                  //unicast_all_summary_established_wide
                leaf unicast_all_summary_established_wide_json {
                    type enumeration {
                        enum unicast_all_summary_established_wide_json;
                    }
                }                  //json
                leaf unicast_all_summary_failed_terse {
                    type enumeration {
                        enum unicast_all_summary_failed_terse;
                    }
                }                  //unicast_all_summary_failed_terse
                leaf unicast_all_summary_failed_terse_json {
                    type enumeration {
                        enum unicast_all_summary_failed_terse_json;
                    }
                }                  //json
                leaf unicast_all_summary_failed_wide {
                    type enumeration {
                        enum unicast_all_summary_failed_wide;
                    }
                }                  //unicast_all_summary_failed_wide
                leaf unicast_all_summary_failed_wide_json {
                    type enumeration {
                        enum unicast_all_summary_failed_wide_json;
                    }
                }                  //json
                leaf unicast_all_summary_terse_wide {
                    type enumeration {
                        enum unicast_all_summary_terse_wide;
                    }
                }                  //unicast_all_summary_terse_wide
                leaf unicast_all_summary_terse_wide_json {
                    type enumeration {
                        enum unicast_all_summary_terse_wide_json;
                    }
                }                  //json
                leaf unicast_community_local-AS_exact-match_json {
                    type enumeration {
                        enum unicast_community_local-AS_exact-match_json;
                    }
                }                  //unicast_community_local-AS_exact-match_json
                leaf unicast_community_local-AS_exact-match_json_detail {
                    type enumeration {
                        enum unicast_community_local-AS_exact-match_json_detail;
                    }
                }                  //detail
                leaf unicast_community_no-advertise_exact-match_json {
                    type enumeration {
                        enum unicast_community_no-advertise_exact-match_json;
                    }
                }                  //unicast_community_no-advertise_exact-match_json
                leaf unicast_community_no-advertise_exact-match_json_detail {
                    type enumeration {
                        enum unicast_community_no-advertise_exact-match_json_detail;
                    }
                }                  //detail
                leaf unicast_community_no-export_exact-match_json {
                    type enumeration {
                        enum unicast_community_no-export_exact-match_json;
                    }
                }                  //unicast_community_no-export_exact-match_json
                leaf unicast_community_no-export_exact-match_json_detail {
                    type enumeration {
                        enum unicast_community_no-export_exact-match_json_detail;
                    }
                }                  //detail
                leaf unicast_community_graceful-shutdown_exact-match_json {
                    type enumeration {
                        enum unicast_community_graceful-shutdown_exact-match_json;
                    }
                }                  //unicast_community_graceful-shutdown_exact-match_json
                leaf unicast_community_graceful-shutdown_exact-match_json_detail {
                    type enumeration {
                        enum unicast_community_graceful-shutdown_exact-match_json_detail;
                    }
                }                  //detail
                leaf unicast_community_no-peer_exact-match_json {
                    type enumeration {
                        enum unicast_community_no-peer_exact-match_json;
                    }
                }                  //unicast_community_no-peer_exact-match_json
                leaf unicast_community_no-peer_exact-match_json_detail {
                    type enumeration {
                        enum unicast_community_no-peer_exact-match_json_detail;
                    }
                }                  //detail
                leaf unicast_community_blackhole_exact-match_json {
                    type enumeration {
                        enum unicast_community_blackhole_exact-match_json;
                    }
                }                  //unicast_community_blackhole_exact-match_json
                leaf unicast_community_blackhole_exact-match_json_detail {
                    type enumeration {
                        enum unicast_community_blackhole_exact-match_json_detail;
                    }
                }                  //detail
                leaf unicast_community_llgr-stale_exact-match_json {
                    type enumeration {
                        enum unicast_community_llgr-stale_exact-match_json;
                    }
                }                  //unicast_community_llgr-stale_exact-match_json
                leaf unicast_community_llgr-stale_exact-match_json_detail {
                    type enumeration {
                        enum unicast_community_llgr-stale_exact-match_json_detail;
                    }
                }                  //detail
                leaf unicast_community_no-llgr_exact-match_json {
                    type enumeration {
                        enum unicast_community_no-llgr_exact-match_json;
                    }
                }                  //unicast_community_no-llgr_exact-match_json
                leaf unicast_community_no-llgr_exact-match_json_detail {
                    type enumeration {
                        enum unicast_community_no-llgr_exact-match_json_detail;
                    }
                }                  //detail
                leaf unicast_community_accept-own_exact-match_json {
                    type enumeration {
                        enum unicast_community_accept-own_exact-match_json;
                    }
                }                  //unicast_community_accept-own_exact-match_json
                leaf unicast_community_accept-own_exact-match_json_detail {
                    type enumeration {
                        enum unicast_community_accept-own_exact-match_json_detail;
                    }
                }                  //detail
                leaf unicast_community_accept-own-nexthop_exact-match_json {
                    type enumeration {
                        enum unicast_community_accept-own-nexthop_exact-match_json;
                    }
                }                  //unicast_community_accept-own-nexthop_exact-match_json
                leaf unicast_community_accept-own-nexthop_exact-match_json_detail {
                    type enumeration {
                        enum unicast_community_accept-own-nexthop_exact-match_json_detail;
                    }
                }                  //detail
                leaf unicast_community_route-filter-v6_exact-match_json {
                    type enumeration {
                        enum unicast_community_route-filter-v6_exact-match_json;
                    }
                }                  //unicast_community_route-filter-v6_exact-match_json
                leaf unicast_community_route-filter-v6_exact-match_json_detail {
                    type enumeration {
                        enum unicast_community_route-filter-v6_exact-match_json_detail;
                    }
                }                  //detail
                leaf unicast_community_route-filter-v4_exact-match_json {
                    type enumeration {
                        enum unicast_community_route-filter-v4_exact-match_json;
                    }
                }                  //unicast_community_route-filter-v4_exact-match_json
                leaf unicast_community_route-filter-v4_exact-match_json_detail {
                    type enumeration {
                        enum unicast_community_route-filter-v4_exact-match_json_detail;
                    }
                }                  //detail
                leaf unicast_community_route-filter-translated-v6_exact-match_json {
                    type enumeration {
                        enum unicast_community_route-filter-translated-v6_exact-match_json;
                    }
                }                  //unicast_community_route-filter-translated-v6_exact-match_json
                leaf unicast_community_route-filter-translated-v6_exact-match_json_detail {
                    type enumeration {
                        enum unicast_community_route-filter-translated-v6_exact-match_json_detail;
                    }
                }                  //detail
                leaf unicast_community_route-filter-translated-v4_exact-match_json {
                    type enumeration {
                        enum unicast_community_route-filter-translated-v4_exact-match_json;
                    }
                }                  //unicast_community_route-filter-translated-v4_exact-match_json
                leaf unicast_community_route-filter-translated-v4_exact-match_json_detail {
                    type enumeration {
                        enum unicast_community_route-filter-translated-v4_exact-match_json_detail;
                    }
                }                  //detail
                leaf unicast_summary_established_terse_wide {
                    type enumeration {
                        enum unicast_summary_established_terse_wide;
                    }
                }                  //unicast_summary_established_terse_wide
                leaf unicast_summary_established_terse_wide_json {
                    type enumeration {
                        enum unicast_summary_established_terse_wide_json;
                    }
                }                  //json
                leaf unicast_summary_failed_terse_wide {
                    type enumeration {
                        enum unicast_summary_failed_terse_wide;
                    }
                }                  //unicast_summary_failed_terse_wide
                leaf unicast_summary_failed_terse_wide_json {
                    type enumeration {
                        enum unicast_summary_failed_terse_wide_json;
                    }
                }                  //json
                leaf unicast_all_community_local-AS_exact-match_json {
                    type enumeration {
                        enum unicast_all_community_local-AS_exact-match_json;
                    }
                }                  //unicast_all_community_local-AS_exact-match_json
                leaf unicast_all_community_local-AS_exact-match_json_detail {
                    type enumeration {
                        enum unicast_all_community_local-AS_exact-match_json_detail;
                    }
                }                  //detail
                leaf unicast_all_community_no-advertise_exact-match_json {
                    type enumeration {
                        enum unicast_all_community_no-advertise_exact-match_json;
                    }
                }                  //unicast_all_community_no-advertise_exact-match_json
                leaf unicast_all_community_no-advertise_exact-match_json_detail {
                    type enumeration {
                        enum unicast_all_community_no-advertise_exact-match_json_detail;
                    }
                }                  //detail
                leaf unicast_all_community_no-export_exact-match_json {
                    type enumeration {
                        enum unicast_all_community_no-export_exact-match_json;
                    }
                }                  //unicast_all_community_no-export_exact-match_json
                leaf unicast_all_community_no-export_exact-match_json_detail {
                    type enumeration {
                        enum unicast_all_community_no-export_exact-match_json_detail;
                    }
                }                  //detail
                leaf unicast_all_community_graceful-shutdown_exact-match_json {
                    type enumeration {
                        enum unicast_all_community_graceful-shutdown_exact-match_json;
                    }
                }                  //unicast_all_community_graceful-shutdown_exact-match_json
                leaf unicast_all_community_graceful-shutdown_exact-match_json_detail {
                    type enumeration {
                        enum unicast_all_community_graceful-shutdown_exact-match_json_detail;
                    }
                }                  //detail
                leaf unicast_all_community_no-peer_exact-match_json {
                    type enumeration {
                        enum unicast_all_community_no-peer_exact-match_json;
                    }
                }                  //unicast_all_community_no-peer_exact-match_json
                leaf unicast_all_community_no-peer_exact-match_json_detail {
                    type enumeration {
                        enum unicast_all_community_no-peer_exact-match_json_detail;
                    }
                }                  //detail
                leaf unicast_all_community_blackhole_exact-match_json {
                    type enumeration {
                        enum unicast_all_community_blackhole_exact-match_json;
                    }
                }                  //unicast_all_community_blackhole_exact-match_json
                leaf unicast_all_community_blackhole_exact-match_json_detail {
                    type enumeration {
                        enum unicast_all_community_blackhole_exact-match_json_detail;
                    }
                }                  //detail
                leaf unicast_all_community_llgr-stale_exact-match_json {
                    type enumeration {
                        enum unicast_all_community_llgr-stale_exact-match_json;
                    }
                }                  //unicast_all_community_llgr-stale_exact-match_json
                leaf unicast_all_community_llgr-stale_exact-match_json_detail {
                    type enumeration {
                        enum unicast_all_community_llgr-stale_exact-match_json_detail;
                    }
                }                  //detail
                leaf unicast_all_community_no-llgr_exact-match_json {
                    type enumeration {
                        enum unicast_all_community_no-llgr_exact-match_json;
                    }
                }                  //unicast_all_community_no-llgr_exact-match_json
                leaf unicast_all_community_no-llgr_exact-match_json_detail {
                    type enumeration {
                        enum unicast_all_community_no-llgr_exact-match_json_detail;
                    }
                }                  //detail
                leaf unicast_all_community_accept-own_exact-match_json {
                    type enumeration {
                        enum unicast_all_community_accept-own_exact-match_json;
                    }
                }                  //unicast_all_community_accept-own_exact-match_json
                leaf unicast_all_community_accept-own_exact-match_json_detail {
                    type enumeration {
                        enum unicast_all_community_accept-own_exact-match_json_detail;
                    }
                }                  //detail
                leaf unicast_all_community_accept-own-nexthop_exact-match_json {
                    type enumeration {
                        enum unicast_all_community_accept-own-nexthop_exact-match_json;
                    }
                }                  //unicast_all_community_accept-own-nexthop_exact-match_json
                leaf unicast_all_community_accept-own-nexthop_exact-match_json_detail {
                    type enumeration {
                        enum unicast_all_community_accept-own-nexthop_exact-match_json_detail;
                    }
                }                  //detail
                leaf unicast_all_community_route-filter-v6_exact-match_json {
                    type enumeration {
                        enum unicast_all_community_route-filter-v6_exact-match_json;
                    }
                }                  //unicast_all_community_route-filter-v6_exact-match_json
                leaf unicast_all_community_route-filter-v6_exact-match_json_detail {
                    type enumeration {
                        enum unicast_all_community_route-filter-v6_exact-match_json_detail;
                    }
                }                  //detail
                leaf unicast_all_community_route-filter-v4_exact-match_json {
                    type enumeration {
                        enum unicast_all_community_route-filter-v4_exact-match_json;
                    }
                }                  //unicast_all_community_route-filter-v4_exact-match_json
                leaf unicast_all_community_route-filter-v4_exact-match_json_detail {
                    type enumeration {
                        enum unicast_all_community_route-filter-v4_exact-match_json_detail;
                    }
                }                  //detail
                leaf unicast_all_community_route-filter-translated-v6_exact-match_json {
                    type enumeration {
                        enum unicast_all_community_route-filter-translated-v6_exact-match_json;
                    }
                }                  //unicast_all_community_route-filter-translated-v6_exact-match_json
                leaf unicast_all_community_route-filter-translated-v6_exact-match_json_detail {
                    type enumeration {
                        enum unicast_all_community_route-filter-translated-v6_exact-match_json_detail;
                    }
                }                  //detail
                leaf unicast_all_community_route-filter-translated-v4_exact-match_json {
                    type enumeration {
                        enum unicast_all_community_route-filter-translated-v4_exact-match_json;
                    }
                }                  //unicast_all_community_route-filter-translated-v4_exact-match_json
                leaf unicast_all_community_route-filter-translated-v4_exact-match_json_detail {
                    type enumeration {
                        enum unicast_all_community_route-filter-translated-v4_exact-match_json_detail;
                    }
                }                  //detail
                leaf unicast_all_summary_established_terse_wide {
                    type enumeration {
                        enum unicast_all_summary_established_terse_wide;
                    }
                }                  //unicast_all_summary_established_terse_wide
                leaf unicast_all_summary_established_terse_wide_json {
                    type enumeration {
                        enum unicast_all_summary_established_terse_wide_json;
                    }
                }                  //json
                leaf unicast_all_summary_failed_terse_wide {
                    type enumeration {
                        enum unicast_all_summary_failed_terse_wide;
                    }
                }                  //unicast_all_summary_failed_terse_wide
                leaf unicast_all_summary_failed_terse_wide_json {
                    type enumeration {
                        enum unicast_all_summary_failed_terse_wide_json;
                    }
                }                  //json
                leaf attribute-info {
                    type enumeration {
                        enum attribute-info;
                    }
                }                  //attribute-info
                leaf community-info {
                    type enumeration {
                        enum community-info;
                    }
                }                  //community-info
                leaf memory {
                    type enumeration {
                        enum memory;
                    }
                }                  //memory
                leaf views {
                    type enumeration {
                        enum views;
                    }
                }                  //views
                leaf large-community-info {
                    type enumeration {
                        enum large-community-info;
                    }
                }                  //large-community-info
            }
            container show_ip_router-id {
                leaf vrf {
                    type enumeration {
                        enum vrf;
                    }
                }                  //vrf
                leaf THE_VRF_NAME {
                    type string;
                }                  //NAME
            }
            container show_ip_as-path-access-list {
                leaf AS_PATH_ACCESS_LIST {
                    type string;
                }                  //AS_PATH_FILTER_NAME
                leaf json {
                    type enumeration {
                        enum json;
                    }
                }                  //json
            }
            container show_ip_mroute {
                leaf THE_SOURCE_OR_GROUP {
                    type inet:ipv4-address;
                }                  //A.B.C.D
                leaf THE_GROUP {
                    type inet:ipv4-address;
                }                  //A.B.C.D
                leaf fill {
                    type enumeration {
                        enum fill;
                    }
                }                  //fill
                leaf fill_json {
                    type enumeration {
                        enum fill_json;
                    }
                }                  //json
                leaf json {
                    type enumeration {
                        enum json;
                    }
                }                  //json
            }
            container show_ip_nht {
                leaf IP_ADDRESS {
                    type union {
                        type inet:ipv4-address;
                        type inet:ipv6-address;
                    }
                }                  //<A.B.C.D|X:X::X:X>
                leaf mrib {
                    type enumeration {
                        enum mrib;
                    }
                }                  //mrib
                leaf mrib_json {
                    type enumeration {
                        enum mrib_json;
                    }
                }                  //json
                leaf json {
                    type enumeration {
                        enum json;
                    }
                }                  //json
            }
            container show_ip_import-check {
                leaf IP_ADDRESS {
                    type union {
                        type inet:ipv4-address;
                        type inet:ipv6-address;
                    }
                }                  //<A.B.C.D|X:X::X:X>
                leaf mrib {
                    type enumeration {
                        enum mrib;
                    }
                }                  //mrib
                leaf mrib_json {
                    type enumeration {
                        enum mrib_json;
                    }
                }                  //json
                leaf json {
                    type enumeration {
                        enum json;
                    }
                }                  //json
            }
            container show_ip_ospf {
                leaf INSTANCE_ID {
                    type int32;
                }                  //(1-65535)
                leaf json {
                    type enumeration {
                        enum json;
                    }
                }                  //json
                leaf border-routers {
                    type enumeration {
                        enum border-routers;
                    }
                }                  //border-routers
                leaf database {
                    type enumeration {
                        enum database;
                    }
                }                  //database
                leaf OSPF_LSA_TYPE {
                    type enumeration {
                        enum asbr-summary;
                        enum external;
                        enum network;
                        enum router;
                        enum summary;
                        enum nssa-external;
                        enum opaque-link;
                        enum opaque-area;
                        enum opaque-as;
                    }
                }                  //<asbr-summary|external|network|router|summary|nssa-external|opaque-link|opaque-area|opaque-as> ['ASBR summary link states', 'External link states', 'Network link states', 'Router link states', 'Network summary link states', 'NSSA external link state', 'Link local Opaque-LSA', 'Link area Opaque-LSA', 'Link AS Opaque-LSA']
                leaf adv-router {
                    type inet:ipv4-address;
                }                  //A.B.C.D
                leaf self-originate {
                    type enumeration {
                        enum self-originate;
                    }
                }
                leaf LINK_STATE_ID {
                    type inet:ipv4-address;
                }                  //A.B.C.D
                leaf LSA_STATUS {
                    type enumeration {
                        enum max-age;
                        enum self-originate;
                    }
                }                  //<max-age|self-originate> ['LSAs in MaxAge list', 'Self-originated link states']
                leaf database_json {
                    type enumeration {
                        enum database_json;
                    }
                }                  //json
                leaf interface {
                    type enumeration {
                        enum interface;
                    }
                }                  //interface
                leaf interface_json {
                    type enumeration {
                        enum interface_json;
                    }
                }                  //json
                leaf neighbor {
                    type enumeration {
                        enum neighbor;
                    }
                }                  //neighbor
                leaf neighbor_json {
                    type enumeration {
                        enum neighbor_json;
                    }
                }                  //json
                leaf reachable-routers {
                    type enumeration {
                        enum reachable-routers;
                    }
                }                  //reachable-routers
                leaf route {
                    type enumeration {
                        enum route;
                    }
                }                  //route
                leaf neighbor_all {
                    type enumeration {
                        enum neighbor_all;
                    }
                }                  //neighbor_all
                leaf neighbor_all_json {
                    type enumeration {
                        enum neighbor_all_json;
                    }
                }                  //json
                leaf neighbor_detail {
                    type enumeration {
                        enum neighbor_detail;
                    }
                }                  //neighbor_detail
                leaf neighbor_detail_json {
                    type enumeration {
                        enum neighbor_detail_json;
                    }
                }                  //json
                leaf neighbor_detail_all {
                    type enumeration {
                        enum neighbor_detail_all;
                    }
                }                  //neighbor_detail_all
                leaf neighbor_detail_all_json {
                    type enumeration {
                        enum neighbor_detail_all_json;
                    }
                }                  //json
            }
            container show_ip_pim {
                leaf assert {
                    type enumeration {
                        enum assert;
                    }
                }                  //assert
                leaf assert-internal {
                    type enumeration {
                        enum assert-internal;
                    }
                }                  //assert-internal
                leaf assert-metric {
                    type enumeration {
                        enum assert-metric;
                    }
                }                  //assert-metric
                leaf assert-winner-metric {
                    type enumeration {
                        enum assert-winner-metric;
                    }
                }                  //assert-winner-metric
                leaf jp-agg {
                    type enumeration {
                        enum jp-agg;
                    }
                }                  //jp-agg
                leaf nexthop-lookup {
                    type enumeration {
                        enum nexthop-lookup;
                    }
                }                  //nexthop-lookup
                leaf SOURCERP_ADDRESS {
                    type inet:ipv4-address;
                }                  //A.B.C.D
                leaf MULTICAST_GROUP_ADDRESS {
                    type inet:ipv4-address;
                }                  //A.B.C.D
                leaf secondary {
                    type enumeration {
                        enum secondary;
                    }
                }                  //secondary
            }
            container show_ip_protocol {
                leaf vrf {
                    type enumeration {
                        enum vrf;
                    }
                }                  //vrf
                leaf THE_VRF_NAME {
                    type string;
                }                  //NAME
                leaf all {
                    type enumeration {
                        enum all;
                    }
                }
            }
            container show_ip_rib {
                leaf vrf {
                    type enumeration {
                        enum vrf;
                    }
                }                  //vrf
                leaf THE_VRF_NAME {
                    type string;
                }                  //NAME
                leaf UNICAST_ADDRESS {
                    type inet:ipv4-address;
                }                  //A.B.C.D
            }
            container show_ip_rip {
                leaf vrf {
                    type enumeration {
                        enum vrf;
                    }
                }                  //vrf
                leaf THE_VRF_NAME {
                    type string;
                }                  //NAME
                leaf status {
                    type enumeration {
                        enum status;
                    }
                }                  //status
            }
            container show_ip_rpf {
                leaf IP_MULTICAST_SOURCE_ADDRESS {
                    type inet:ipv4-address;
                }                  //A.B.C.D
                leaf json {
                    type enumeration {
                        enum json;
                    }
                }                  //json
            }
            container show_ip_ssmpingd {
                leaf vrf {
                    type enumeration {
                        enum vrf;
                    }
                }                  //vrf
                leaf THE_VRF_NAME {
                    type string;
                }                  //NAME
            }
            container show_ip_access-list {
                leaf IP_ACCESS-LIST_NAME {
                    type string;
                }                  //ACCESSLIST4_NAME
                leaf json {
                    type enumeration {
                        enum json;
                    }
                }                  //json
            }
            container show_ipv6_nhrp {
                leaf json {
                    type enumeration {
                        enum json;
                    }
                }                  //json
            }
            container show_ipv6_route {
                leaf vrf {
                    type enumeration {
                        enum vrf;
                    }
                }                  //vrf
                leaf THE_VRF_NAME {
                    type string;
                }                  //NAME
                leaf all {
                    type enumeration {
                        enum all;
                    }
                }
                leaf summary {
                    type enumeration {
                        enum summary;
                    }
                }                  //summary
                leaf summary_table {
                    type enumeration {
                        enum summary_table;
                    }
                }                  //table
                leaf THE_TABLE_NUMBER {
                    type int32;
                }                  //(1-4294967295)
                leaf prefix {
                    type enumeration {
                        enum prefix;
                    }
                }                  //prefix
                leaf prefix_json {
                    type enumeration {
                        enum prefix_json;
                    }
                }                  //json
                leaf json {
                    type enumeration {
                        enum json;
                    }
                }                  //json
                leaf summary_json {
                    type enumeration {
                        enum summary_json;
                    }
                }                  //json
                leaf summary_prefix {
                    type enumeration {
                        enum summary_prefix;
                    }
                }                  //summary_prefix
                leaf summary_prefix_json {
                    type enumeration {
                        enum summary_prefix_json;
                    }
                }                  //json
            }
            container show_ipv6_router-id {
                leaf vrf {
                    type enumeration {
                        enum vrf;
                    }
                }                  //vrf
                leaf THE_VRF_NAME {
                    type string;
                }                  //NAME
            }
            container show_ipv6_mroute {
                leaf THE_SOURCE_OR_GROUP {
                    type inet:ipv6-address;
                }                  //X:X::X:X
                leaf THE_GROUP {
                    type inet:ipv6-address;
                }                  //X:X::X:X
                leaf fill {
                    type enumeration {
                        enum fill;
                    }
                }                  //fill
                leaf fill_json {
                    type enumeration {
                        enum fill_json;
                    }
                }                  //json
                leaf json {
                    type enumeration {
                        enum json;
                    }
                }                  //json
            }
            container show_ipv6_nht {
                leaf IP_ADDRESS {
                    type union {
                        type inet:ipv4-address;
                        type inet:ipv6-address;
                    }
                }                  //<A.B.C.D|X:X::X:X>
                leaf mrib {
                    type enumeration {
                        enum mrib;
                    }
                }                  //mrib
                leaf mrib_json {
                    type enumeration {
                        enum mrib_json;
                    }
                }                  //json
                leaf json {
                    type enumeration {
                        enum json;
                    }
                }                  //json
            }
            container show_ipv6_import-check {
                leaf IP_ADDRESS {
                    type union {
                        type inet:ipv4-address;
                        type inet:ipv6-address;
                    }
                }                  //<A.B.C.D|X:X::X:X>
                leaf mrib {
                    type enumeration {
                        enum mrib;
                    }
                }                  //mrib
                leaf mrib_json {
                    type enumeration {
                        enum mrib_json;
                    }
                }                  //json
                leaf json {
                    type enumeration {
                        enum json;
                    }
                }                  //json
            }
            container show_ipv6_ospf6 {
                leaf vrf {
                    type enumeration {
                        enum vrf;
                    }
                }                  //vrf
                leaf THE_VRF_NAME {
                    type string;
                }                  //NAME
                leaf all {
                    type enumeration {
                        enum all;
                    }
                }
                leaf json {
                    type enumeration {
                        enum json;
                    }
                }                  //json
                leaf area {
                    type enumeration {
                        enum area;
                    }
                }                  //area
                leaf AREA_ID {
                    type inet:ipv4-address;
                }                  //A.B.C.D
                leaf spf_tree {
                    type enumeration {
                        enum spf_tree;
                    }
                }                  //tree
                leaf border-routers {
                    type enumeration {
                        enum border-routers;
                    }
                }                  //border-routers
                leaf ROUTER_ID {
                    type inet:ipv4-address;
                }                  //A.B.C.D
                leaf detail {
                    type enumeration {
                        enum detail;
                    }
                }
                leaf database {
                    type enumeration {
                        enum database;
                    }
                }                  //database
                leaf ANY_LINK_STATE_TYPE {
                    type string;
                }                  //*
                leaf linkstate-id {
                    type enumeration {
                        enum linkstate-id;
                    }
                }
                leaf SPECIFY_LINK_STATE_ID {
                    type inet:ipv4-address;
                }                  //A.B.C.D
                leaf CHOICE_CASE {
                    type enumeration {
                        enum detail;
                        enum dump;
                        enum internal;
                    }
                }                  //<detail|dump|internal> ['Display details of LSAs', 'Dump LSAs', "Display LSA's internal information"]
                leaf SPECIFY_ADVERTISING_ROUTER_AS {
                    type inet:ipv4-address;
                }                  //A.B.C.D
                leaf self-originated {
                    type enumeration {
                        enum self-originated;
                    }
                }                  //self-originated
                leaf self-originated_json {
                    type enumeration {
                        enum self-originated_json;
                    }
                }                  //json
                leaf adv-router {
                    type enumeration {
                        enum adv-router;
                    }
                }                  //adv-router
                leaf ANY_LINK_STATE_ID {
                    type string;
                }                  //*
                leaf self-originated_linkstate-id {
                    type enumeration {
                        enum self-originated_linkstate-id;
                    }
                }                  //linkstate-id
                leaf database_json {
                    type enumeration {
                        enum database_json;
                    }
                }                  //json
                leaf interface {
                    type enumeration {
                        enum interface;
                    }
                }                  //interface
                leaf interface_json {
                    type enumeration {
                        enum interface_json;
                    }
                }                  //json
                leaf linkstate {
                    type enumeration {
                        enum linkstate;
                    }
                }                  //linkstate
                leaf router {
                    type inet:ipv4-address;
                }                  //A.B.C.D
                leaf network {
                    type inet:ipv4-address;
                }                  //A.B.C.D
                leaf DISPLAY_NETWORK_ENTRY {
                    type inet:ipv4-address;
                }                  //A.B.C.D
                leaf neighbor {
                    type enumeration {
                        enum neighbor;
                    }
                }                  //neighbor
                leaf neighbor_json {
                    type enumeration {
                        enum neighbor_json;
                    }
                }                  //json
                leaf redistribute {
                    type enumeration {
                        enum redistribute;
                    }
                }                  //redistribute
                leaf redistribute_json {
                    type enumeration {
                        enum redistribute_json;
                    }
                }                  //json
                leaf route {
                    type enumeration {
                        enum route;
                    }
                }                  //route
                leaf ROUTE_TYPE_FILTER {
                    type enumeration {
                        enum intra-area;
                        enum inter-area;
                        enum external-1;
                        enum external-2;
                    }
                }                  //<intra-area|inter-area|external-1|external-2> ['Display Intra-Area routes', 'Display Inter-Area routes', 'Display Type-1 External routes', 'Display Type-2 External routes']
                leaf detail_json {
                    type enumeration {
                        enum detail_json;
                    }
                }                  //json
                leaf SPECIFY_IPV6_ADDRESS {
                    type union {
                        type inet:ipv6-address;
                        type inet:ipv6-prefix;
                    }
                }                  //<X:X::X:X|X:X::X:X/M>
                leaf ROUTE_FILTER_DETAIL_SUMMARY {
                    type enumeration {
                        enum intra-area;
                        enum inter-area;
                        enum external-1;
                        enum external-2;
                        enum detail;
                        enum summary;
                    }
                }                  //<intra-area|inter-area|external-1|external-2|detail|summary> ['Display Intra-Area routes', 'Display Inter-Area routes', 'Display Type-1 External routes', 'Display Type-2 External routes', 'Specify IPv6 address', 'Specify IPv6 prefix', 'Detailed information', 'Summary of route table']
                leaf route_json {
                    type enumeration {
                        enum route_json;
                    }
                }                  //json
                leaf simulate_spf-tree {
                    type enumeration {
                        enum simulate_spf-tree;
                    }
                }                  //spf-tree
                leaf SPECIFY_ROOT_ROUTER-ID_TO {
                    type inet:ipv4-address;
                }                  //A.B.C.D
                leaf summary-address {
                    type enumeration {
                        enum summary-address;
                    }
                }                  //summary-address
                leaf summary-address_json {
                    type enumeration {
                        enum summary-address_json;
                    }
                }                  //json
                leaf database_adv-router {
                    type enumeration {
                        enum database_adv-router;
                    }
                }                  //database_adv-router
                leaf database_aggr_adv-router {
                    type enumeration {
                        enum database_aggr_adv-router;
                    }
                }                  //adv-router
                leaf database_self-originated {
                    type enumeration {
                        enum database_self-originated;
                    }
                }                  //database_self-originated
                leaf database_self-originated_json {
                    type enumeration {
                        enum database_self-originated_json;
                    }
                }                  //json
                leaf interface_prefix {
                    type enumeration {
                        enum interface_prefix;
                    }
                }                  //interface_prefix
                leaf OSPF6_ROUTE_ADDRESS_STR {
                    type union {
                        type inet:ipv6-address;
                        type inet:ipv6-prefix;
                    }
                }                  //<X:X::X:X|X:X::X:X/M>
                leaf ROUTE_PREFIX_MATCH_DETAIL {
                    type enumeration {
                        enum match;
                        enum detail;
                    }
                }                  //<match|detail> ['Display details of the prefixes', 'JavaScript Object Notation']
                leaf interface_prefix_json {
                    type enumeration {
                        enum interface_prefix_json;
                    }
                }                  //json
                leaf interface_traffic {
                    type enumeration {
                        enum interface_traffic;
                    }
                }                  //interface_traffic
                leaf interface_traffic_json {
                    type enumeration {
                        enum interface_traffic_json;
                    }
                }                  //json
                leaf spf_tree_json {
                    type enumeration {
                        enum spf_tree_json;
                    }
                }                  //json
                leaf summary-address_detail {
                    type enumeration {
                        enum summary-address_detail;
                    }
                }                  //summary-address_detail
                leaf summary-address_detail_json {
                    type enumeration {
                        enum summary-address_detail_json;
                    }
                }                  //json
                leaf interface_prefix_detail {
                    type enumeration {
                        enum interface_prefix_detail;
                    }
                }                  //interface_prefix_detail
                leaf interface_prefix_detail_json {
                    type enumeration {
                        enum interface_prefix_detail_json;
                    }
                }                  //json
            }
            container show_ipv6_pim {
                leaf jp-agg {
                    type enumeration {
                        enum jp-agg;
                    }
                }                  //jp-agg
                leaf nexthop-lookup {
                    type enumeration {
                        enum nexthop-lookup;
                    }
                }                  //nexthop-lookup
                leaf SOURCERP_ADDRESS {
                    type inet:ipv6-address;
                }                  //X:X::X:X
                leaf MULTICAST_GROUP_ADDRESS {
                    type inet:ipv6-address;
                }                  //X:X::X:X
                leaf secondary {
                    type enumeration {
                        enum secondary;
                    }
                }                  //secondary
            }
            container show_ipv6_protocol {
                leaf vrf {
                    type enumeration {
                        enum vrf;
                    }
                }                  //vrf
                leaf THE_VRF_NAME {
                    type string;
                }                  //NAME
                leaf all {
                    type enumeration {
                        enum all;
                    }
                }
            }
            container show_ipv6_ripng {
                leaf vrf {
                    type enumeration {
                        enum vrf;
                    }
                }                  //vrf
                leaf THE_VRF_NAME {
                    type string;
                }                  //NAME
                leaf status {
                    type enumeration {
                        enum status;
                    }
                }                  //status
            }
            container show_ipv6_access-list {
                leaf IPV6_ACCESS-LIST_NAME {
                    type string;
                }                  //ACCESSLIST6_NAME
                leaf json {
                    type enumeration {
                        enum json;
                    }
                }                  //json
            }
            container show_nexthop-group_rib {
                leaf NEXTHOP_GROUP_ID {
                    type int32;
                }                  //(0-4294967295)
                leaf json {
                    type enumeration {
                        enum json;
                    }
                }                  //json
                leaf singleton {
                    type enumeration {
                        enum singleton;
                    }
                }                  //singleton
                leaf LABEL_FORWARD {
                    type enumeration {
                        enum ip;
                        enum ipv6;
                    }
                }                  //<ip|ipv6> ['IP information', 'IPv6 Information']
                leaf CHOICE_CASE {
                    type enumeration {
                        enum kernel;
                        enum zebra;
                        enum bgp;
                        enum sharp;
                    }
                }                  //<kernel|zebra|bgp|sharp> ['Kernel (not installed via the zebra RIB)', 'Zebra (implicitly created by zebra)', 'Border Gateway Protocol (BGP)', 'Super Happy Advanced Routing Protocol (SHARP)']
                leaf vrf {
                    type enumeration {
                        enum vrf;
                    }
                }                  //vrf
                leaf THE_VRF_NAME {
                    type string;
                }                  //NAME
                leaf all {
                    type enumeration {
                        enum all;
                    }
                }
            }
            container show_bgp_update-groups {
                leaf SPECIFIC_SUBGROUP_TO_DISPLAY {
                    type string;
                }                  //SUBGROUP-ID
                leaf ROUTING_QUEUE {
                    type enumeration {
                        enum advertise-queue;
                        enum advertised-routes;
                        enum packet-queue;
                    }
                }                  //<advertise-queue|advertised-routes|packet-queue> ['Advertisement queue', 'Announced routes', 'Packet queue']
                leaf json {
                    type enumeration {
                        enum json;
                    }
                }                  //json
                leaf statistics {
                    type enumeration {
                        enum statistics;
                    }
                }                  //statistics
            }
            container show_bgp_route-leak {
                leaf json {
                    type enumeration {
                        enum json;
                    }
                }                  //json
            }
            container show_bgp_all {
                leaf community-list {
                    type enumeration {
                        enum community-list;
                    }
                }                  //community-list
                leaf COMMUNITY-LIST_NAME {
                    type union {
                        type int32;
                        type string;
                    }
                }                  //<(1-500)|COMMUNITY_LIST_NAME>
                leaf exact-match {
                    type enumeration {
                        enum exact-match;
                    }
                }                  //exact-match
                leaf exact-match_wide {
                    type enumeration {
                        enum exact-match_wide;
                    }
                }                  //wide
                leaf json {
                    type enumeration {
                        enum json;
                    }
                }                  //json
                leaf json_detail {
                    type enumeration {
                        enum json_detail;
                    }
                }                  //detail
                leaf wide {
                    type enumeration {
                        enum wide;
                    }
                }                  //wide
                leaf exact-match_json {
                    type enumeration {
                        enum exact-match_json;
                    }
                }                  //exact-match_json
                leaf exact-match_json_detail {
                    type enumeration {
                        enum exact-match_json_detail;
                    }
                }                  //detail
                leaf filter-list {
                    type enumeration {
                        enum filter-list;
                    }
                }                  //filter-list
                leaf REGULAR_EXPRESSION_ACCESS_LIST {
                    type string;
                }                  //AS_PATH_FILTER_NAME
                leaf prefix-list {
                    type enumeration {
                        enum prefix-list;
                    }
                }                  //prefix-list
                leaf PREFIX-LIST_NAME {
                    type string;
                }                  //WORD
                leaf access-list {
                    type enumeration {
                        enum access-list;
                    }
                }                  //access-list
                leaf ACCESS-LIST_NAME {
                    type string;
                }                  //ACCESSLIST_NAME
                leaf route-map {
                    type enumeration {
                        enum route-map;
                    }
                }                  //route-map
                leaf A_ROUTE-MAP_TO_MATCH {
                    type string;
                }                  //RMAP_NAME
                leaf rpki {
                    type enumeration {
                        enum rpki;
                    }
                }                  //rpki
                leaf CHOICE_CASE {
                    type enumeration {
                        enum invalid;
                        enum valid;
                        enum notfound;
                    }
                }                  //<invalid|valid|notfound> ['A valid path as determined by rpki', 'A invalid path as determined by rpki', 'A path that has no rpki data']
                leaf version {
                    type enumeration {
                        enum version;
                    }
                }                  //version
                leaf VERSION_NUMBER_AND_ABOVE {
                    type int32;
                }                  //(1-4294967295)
                leaf alias {
                    type enumeration {
                        enum alias;
                    }
                }                  //alias
                leaf BGP_COMMUNITY_ALIAS {
                    type string;
                }                  //ALIAS_NAME
                leaf IPV4_PREFIX {
                    type inet:ipv4-prefix;
                }                  //A.B.C.D/M
                leaf longer-prefixes {
                    type enumeration {
                        enum longer-prefixes;
                    }
                }                  //longer-prefixes
                leaf longer-prefixes_wide {
                    type enumeration {
                        enum longer-prefixes_wide;
                    }
                }                  //wide
                leaf longer-prefixes_json {
                    type enumeration {
                        enum longer-prefixes_json;
                    }
                }                  //longer-prefixes_json
                leaf longer-prefixes_json_detail {
                    type enumeration {
                        enum longer-prefixes_json_detail;
                    }
                }                  //detail
                leaf IPV6_PREFIX {
                    type inet:ipv6-prefix;
                }                  //X:X::X:X/M
                leaf neighbors {
                    type enumeration {
                        enum neighbors;
                    }
                }                  //neighbors
                leaf IP_ADDRESS {
                    type union {
                        type inet:ipv4-address;
                        type inet:ipv6-address;
                        type string;
                    }
                }                  //<A.B.C.D|X:X::X:X|WORD>
                leaf BGP_NEIGHBOR_ROUTE_DIRECTION {
                    type enumeration {
                        enum advertised-routes;
                        enum received-routes;
                        enum filtered-routes;
                    }
                }                  //<advertised-routes|received-routes|filtered-routes> ['Display the routes advertised to a BGP neighbor', 'Display the received routes from neighbor', 'Display the filtered routes received from neighbor']
                leaf detail {
                    type enumeration {
                        enum detail;
                    }
                }                  //detail
                leaf detail_json {
                    type enumeration {
                        enum detail_json;
                    }
                }                  //json
                leaf detail_wide {
                    type enumeration {
                        enum detail_wide;
                    }
                }                  //wide
            }
            container show_bgp_cidr-only {
                leaf wide {
                    type enumeration {
                        enum wide;
                    }
                }                  //wide
            }
            container show_bgp_dampening {
                leaf CHOICE_CASE {
                    type enumeration {
                        enum flap-statistics;
                        enum dampened-paths;
                    }
                }                  //<flap-statistics|dampened-paths> ['Display flap statistics of routes', 'Display paths suppressed due to dampening']
                leaf json {
                    type enumeration {
                        enum json;
                    }
                }                  //json
                leaf json_detail {
                    type enumeration {
                        enum json_detail;
                    }
                }                  //detail
                leaf wide {
                    type enumeration {
                        enum wide;
                    }
                }                  //wide
            }
            container show_bgp_community {
                leaf COMMUNITY_NUMBER {
                    type string;
                }                  //AA:NN
                leaf exact-match {
                    type enumeration {
                        enum exact-match;
                    }
                }                  //exact-match
                leaf exact-match_wide {
                    type enumeration {
                        enum exact-match_wide;
                    }
                }                  //wide
                leaf json {
                    type enumeration {
                        enum json;
                    }
                }                  //json
                leaf json_detail {
                    type enumeration {
                        enum json_detail;
                    }
                }                  //detail
                leaf wide {
                    type enumeration {
                        enum wide;
                    }
                }                  //wide
                leaf exact-match_json {
                    type enumeration {
                        enum exact-match_json;
                    }
                }                  //exact-match_json
                leaf exact-match_json_detail {
                    type enumeration {
                        enum exact-match_json_detail;
                    }
                }                  //detail
            }
            container show_bgp_community-list {
                leaf COMMUNITY-LIST_NAME {
                    type union {
                        type int32;
                        type string;
                    }
                }                  //<(1-500)|COMMUNITY_LIST_NAME>
                leaf exact-match {
                    type enumeration {
                        enum exact-match;
                    }
                }                  //exact-match
                leaf exact-match_wide {
                    type enumeration {
                        enum exact-match_wide;
                    }
                }                  //wide
                leaf json {
                    type enumeration {
                        enum json;
                    }
                }                  //json
                leaf json_detail {
                    type enumeration {
                        enum json_detail;
                    }
                }                  //detail
                leaf wide {
                    type enumeration {
                        enum wide;
                    }
                }                  //wide
                leaf detail {
                    type enumeration {
                        enum detail;
                    }
                }                  //detail
                leaf exact-match_json {
                    type enumeration {
                        enum exact-match_json;
                    }
                }                  //exact-match_json
                leaf exact-match_json_detail {
                    type enumeration {
                        enum exact-match_json_detail;
                    }
                }                  //detail
            }
            container show_bgp_detail-routes {
                leaf wide {
                    type enumeration {
                        enum wide;
                    }
                }                  //wide
            }
            container show_bgp_json {
                leaf detail {
                    type enumeration {
                        enum detail;
                    }
                }                  //detail
            }
            container show_bgp_neighbors {
                leaf IP_ADDRESS {
                    type union {
                        type inet:ipv4-address;
                        type inet:ipv6-address;
                        type string;
                    }
                }                  //<A.B.C.D|X:X::X:X|WORD>
                leaf BGP_NEIGHBOR_ROUTE_DIRECTION {
                    type enumeration {
                        enum advertised-routes;
                        enum received-routes;
                        enum filtered-routes;
                    }
                }                  //<advertised-routes|received-routes|filtered-routes> ['Display the routes advertised to a BGP neighbor', 'Display the received routes from neighbor', 'Display the filtered routes received from neighbor']
                leaf route-map {
                    type enumeration {
                        enum route-map;
                    }
                }                  //route-map
                leaf NAME_OF_THE_ROUTE {
                    type string;
                }                  //RMAP_NAME
                leaf detail {
                    type enumeration {
                        enum detail;
                    }
                }                  //detail
                leaf detail_json {
                    type enumeration {
                        enum detail_json;
                    }
                }                  //json
                leaf detail_wide {
                    type enumeration {
                        enum detail_wide;
                    }
                }                  //wide
                leaf json {
                    type enumeration {
                        enum json;
                    }
                }                  //json
                leaf wide {
                    type enumeration {
                        enum wide;
                    }
                }                  //wide
                leaf BGP_NEIGHBOR_ROUTE_STATS {
                    type enumeration {
                        enum flap-statistics;
                        enum dampened-routes;
                        enum routes;
                    }
                }                  //<flap-statistics|dampened-routes|routes> ['Display flap statistics of the routes learned from neighbor', 'Display the dampened routes received from neighbor', 'Display routes learned from neighbor']
                leaf bestpath-routes {
                    type enumeration {
                        enum bestpath-routes;
                    }
                }                  //bestpath-routes
                leaf bestpath-routes_json {
                    type enumeration {
                        enum bestpath-routes_json;
                    }
                }                  //json
                leaf bestpath-routes_wide {
                    type enumeration {
                        enum bestpath-routes_wide;
                    }
                }                  //wide
                leaf graceful-restart {
                    type enumeration {
                        enum graceful-restart;
                    }
                }                  //graceful-restart
                leaf graceful-restart_json {
                    type enumeration {
                        enum graceful-restart_json;
                    }
                }                  //json
                leaf prefix-counts {
                    type enumeration {
                        enum prefix-counts;
                    }
                }                  //prefix-counts
                leaf prefix-counts_json {
                    type enumeration {
                        enum prefix-counts_json;
                    }
                }                  //json
                leaf received_prefix-filter {
                    type enumeration {
                        enum received_prefix-filter;
                    }
                }                  //received_prefix-filter
                leaf received_prefix-filter_json {
                    type enumeration {
                        enum received_prefix-filter_json;
                    }
                }                  //json
            }
            container show_bgp_summary {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_bgp_large-community {
                leaf LARGE_COMMUNITY {
                    type string;
                }                  //AA:BB:CC
                leaf exact-match {
                    type enumeration {
                        enum exact-match;
                    }
                }                  //exact-match
                leaf exact-match_json {
                    type enumeration {
                        enum exact-match_json;
                    }
                }                  //json
                leaf json {
                    type enumeration {
                        enum json;
                    }
                }                  //json
            }
            container show_bgp_large-community-list {
                leaf LARGE-COMMUNITY-LIST_NUMBER {
                    type union {
                        type int32;
                        type string;
                    }
                }                  //<(1-500)|LCOMMUNITY_LIST_NAME>
                leaf exact-match {
                    type enumeration {
                        enum exact-match;
                    }
                }                  //exact-match
                leaf exact-match_json {
                    type enumeration {
                        enum exact-match_json;
                    }
                }                  //json
                leaf json {
                    type enumeration {
                        enum json;
                    }
                }                  //json
                leaf detail {
                    type enumeration {
                        enum detail;
                    }
                }                  //detail
            }
            container show_bgp_statistics {
                leaf json {
                    type enumeration {
                        enum json;
                    }
                }                  //json
            }
            container show_bgp_detail {
                leaf json {
                    type enumeration {
                        enum json;
                    }
                }                  //json
            }
            container show_bgp_peer-group {
                leaf PEER_GROUP_NAME {
                    type string;
                }                  //PGNAME
                leaf json {
                    type enumeration {
                        enum json;
                    }
                }                  //json
            }
            container show_bgp_statistics-all {
                leaf json {
                    type enumeration {
                        enum json;
                    }
                }                  //json
            }
            container show_bgp_vrfs {
                leaf SPECIFIC_VRF_NAME {
                    type string;
                }                  //VRFNAME
                leaf json {
                    type enumeration {
                        enum json;
                    }
                }                  //json
            }
            container show_bgp_martian {
                leaf next-hop {
                    type enumeration {
                        enum next-hop;
                    }
                }                  //next-hop
            }
            container show_bgp_vrf {
                leaf VIEWVRF_NAME {
                    type string;
                }                  //VIEWVRFNAME
                leaf update-groups {
                    type enumeration {
                        enum update-groups;
                    }
                }                  //update-groups
                leaf update-groups_statistics {
                    type enumeration {
                        enum update-groups_statistics;
                    }
                }                  //statistics
                leaf ROUTING_QUEUE {
                    type enumeration {
                        enum advertise-queue;
                        enum advertised-routes;
                        enum packet-queue;
                    }
                }                  //<advertise-queue|advertised-routes|packet-queue> ['Advertisement queue', 'Announced routes', 'Packet queue']
                leaf update-groups_json {
                    type enumeration {
                        enum update-groups_json;
                    }
                }                  //json
                leaf REDISTRIBUTE_IP {
                    type enumeration {
                        enum ipv4;
                        enum ipv6;
                    }
                }                  //<ipv4|ipv6> ['Address Family', 'Address Family']
                leaf route-leak {
                    type enumeration {
                        enum route-leak;
                    }
                }                  //route-leak
                leaf route-leak_json {
                    type enumeration {
                        enum route-leak_json;
                    }
                }                  //json
                leaf all {
                    type enumeration {
                        enum all;
                    }
                }                  //all
                leaf all_community-list {
                    type enumeration {
                        enum all_community-list;
                    }
                }                  //community-list
                leaf COMMUNITY-LIST_NAME {
                    type union {
                        type int32;
                        type string;
                    }
                }                  //<(1-500)|COMMUNITY_LIST_NAME>
                leaf exact-match {
                    type enumeration {
                        enum exact-match;
                    }
                }                  //exact-match
                leaf exact-match_wide {
                    type enumeration {
                        enum exact-match_wide;
                    }
                }                  //wide
                leaf json {
                    type enumeration {
                        enum json;
                    }
                }                  //json
                leaf json_detail {
                    type enumeration {
                        enum json_detail;
                    }
                }                  //detail
                leaf wide {
                    type enumeration {
                        enum wide;
                    }
                }                  //wide
                leaf exact-match_json {
                    type enumeration {
                        enum exact-match_json;
                    }
                }                  //exact-match_json
                leaf exact-match_json_detail {
                    type enumeration {
                        enum exact-match_json_detail;
                    }
                }                  //detail
                leaf all_filter-list {
                    type enumeration {
                        enum all_filter-list;
                    }
                }                  //filter-list
                leaf REGULAR_EXPRESSION_ACCESS_LIST {
                    type string;
                }                  //AS_PATH_FILTER_NAME
                leaf all_prefix-list {
                    type enumeration {
                        enum all_prefix-list;
                    }
                }                  //prefix-list
                leaf PREFIX-LIST_NAME {
                    type string;
                }                  //WORD
                leaf all_access-list {
                    type enumeration {
                        enum all_access-list;
                    }
                }                  //access-list
                leaf ACCESS-LIST_NAME {
                    type string;
                }                  //ACCESSLIST_NAME
                leaf all_route-map {
                    type enumeration {
                        enum all_route-map;
                    }
                }                  //route-map
                leaf A_ROUTE-MAP_TO_MATCH {
                    type string;
                }                  //RMAP_NAME
                leaf all_rpki {
                    type enumeration {
                        enum all_rpki;
                    }
                }                  //rpki
                leaf CHOICE_CASE {
                    type enumeration {
                        enum invalid;
                        enum valid;
                        enum notfound;
                    }
                }                  //<invalid|valid|notfound> ['A valid path as determined by rpki', 'A invalid path as determined by rpki', 'A path that has no rpki data']
                leaf all_version {
                    type enumeration {
                        enum all_version;
                    }
                }                  //version
                leaf VERSION_NUMBER_AND_ABOVE {
                    type int32;
                }                  //(1-4294967295)
                leaf all_alias {
                    type enumeration {
                        enum all_alias;
                    }
                }                  //alias
                leaf BGP_COMMUNITY_ALIAS {
                    type string;
                }                  //ALIAS_NAME
                leaf all_wide {
                    type enumeration {
                        enum all_wide;
                    }
                }                  //wide
                leaf all_neighbors {
                    type enumeration {
                        enum all_neighbors;
                    }
                }                  //neighbors
                leaf IP_ADDRESS {
                    type union {
                        type inet:ipv4-address;
                        type inet:ipv6-address;
                        type string;
                    }
                }                  //<A.B.C.D|X:X::X:X|WORD>
                leaf BGP_NEIGHBOR_ROUTE_DIRECTION {
                    type enumeration {
                        enum advertised-routes;
                        enum received-routes;
                        enum filtered-routes;
                    }
                }                  //<advertised-routes|received-routes|filtered-routes> ['Display the routes advertised to a BGP neighbor', 'Display the received routes from neighbor', 'Display the filtered routes received from neighbor']
                leaf route-map {
                    type enumeration {
                        enum route-map;
                    }
                }                  //route-map
                leaf NAME_OF_THE_ROUTE {
                    type string;
                }                  //RMAP_NAME
                leaf detail {
                    type enumeration {
                        enum detail;
                    }
                }                  //detail
                leaf detail_json {
                    type enumeration {
                        enum detail_json;
                    }
                }                  //json
                leaf detail_wide {
                    type enumeration {
                        enum detail_wide;
                    }
                }                  //wide
                leaf cidr-only {
                    type enumeration {
                        enum cidr-only;
                    }
                }                  //cidr-only
                leaf cidr-only_wide {
                    type enumeration {
                        enum cidr-only_wide;
                    }
                }                  //wide
                leaf dampening {
                    type enumeration {
                        enum dampening;
                    }
                }                  //dampening
                leaf community {
                    type enumeration {
                        enum community;
                    }
                }                  //community
                leaf community_wide {
                    type enumeration {
                        enum community_wide;
                    }
                }                  //wide
                leaf community-list {
                    type enumeration {
                        enum community-list;
                    }
                }                  //community-list
                leaf filter-list {
                    type enumeration {
                        enum filter-list;
                    }
                }                  //filter-list
                leaf prefix-list {
                    type enumeration {
                        enum prefix-list;
                    }
                }                  //prefix-list
                leaf access-list {
                    type enumeration {
                        enum access-list;
                    }
                }                  //access-list
                leaf rpki {
                    type enumeration {
                        enum rpki;
                    }
                }                  //rpki
                leaf version {
                    type enumeration {
                        enum version;
                    }
                }                  //version
                leaf alias {
                    type enumeration {
                        enum alias;
                    }
                }                  //alias
                leaf IPV4_PREFIX {
                    type inet:ipv4-prefix;
                }                  //A.B.C.D/M
                leaf longer-prefixes {
                    type enumeration {
                        enum longer-prefixes;
                    }
                }                  //longer-prefixes
                leaf longer-prefixes_wide {
                    type enumeration {
                        enum longer-prefixes_wide;
                    }
                }                  //wide
                leaf longer-prefixes_json {
                    type enumeration {
                        enum longer-prefixes_json;
                    }
                }                  //longer-prefixes_json
                leaf longer-prefixes_json_detail {
                    type enumeration {
                        enum longer-prefixes_json_detail;
                    }
                }                  //detail
                leaf IPV6_PREFIX {
                    type inet:ipv6-prefix;
                }                  //X:X::X:X/M
                leaf detail-routes {
                    type enumeration {
                        enum detail-routes;
                    }
                }                  //detail-routes
                leaf detail-routes_wide {
                    type enumeration {
                        enum detail-routes_wide;
                    }
                }                  //wide
                leaf neighbors {
                    type enumeration {
                        enum neighbors;
                    }
                }                  //neighbors
                leaf BGP_NEIGHBOR_ROUTE_STATS {
                    type enumeration {
                        enum flap-statistics;
                        enum dampened-routes;
                        enum routes;
                    }
                }                  //<flap-statistics|dampened-routes|routes> ['Display flap statistics of the routes learned from neighbor', 'Display the dampened routes received from neighbor', 'Display routes learned from neighbor']
                leaf bestpath-routes {
                    type enumeration {
                        enum bestpath-routes;
                    }
                }                  //bestpath-routes
                leaf bestpath-routes_json {
                    type enumeration {
                        enum bestpath-routes_json;
                    }
                }                  //json
                leaf bestpath-routes_wide {
                    type enumeration {
                        enum bestpath-routes_wide;
                    }
                }                  //wide
                leaf received_prefix-filter {
                    type enumeration {
                        enum received_prefix-filter;
                    }
                }                  //received_prefix-filter
                leaf received_prefix-filter_json {
                    type enumeration {
                        enum received_prefix-filter_json;
                    }
                }                  //json
                leaf neighbors_json {
                    type enumeration {
                        enum neighbors_json;
                    }
                }                  //json
                leaf summary {
                    type enumeration {
                        enum summary;
                    }
                }                  //summary
                leaf summary_neighbor {
                    type enumeration {
                        enum summary_neighbor;
                    }
                }                  //neighbor
                leaf terse {
                    type enumeration {
                        enum terse;
                    }
                }                  //terse
                leaf terse_json {
                    type enumeration {
                        enum terse_json;
                    }
                }                  //json
                leaf wide_json {
                    type enumeration {
                        enum wide_json;
                    }
                }                  //json
                leaf terse_wide {
                    type enumeration {
                        enum terse_wide;
                    }
                }                  //terse_wide
                leaf terse_wide_json {
                    type enumeration {
                        enum terse_wide_json;
                    }
                }                  //json
                leaf summary_remote-as {
                    type enumeration {
                        enum summary_remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
                leaf summary_json {
                    type enumeration {
                        enum summary_json;
                    }
                }                  //json
                leaf large-community {
                    type enumeration {
                        enum large-community;
                    }
                }                  //large-community
                leaf LARGE_COMMUNITY {
                    type string;
                }                  //AA:BB:CC
                leaf large-community_json {
                    type enumeration {
                        enum large-community_json;
                    }
                }                  //json
                leaf large-community-list {
                    type enumeration {
                        enum large-community-list;
                    }
                }                  //large-community-list
                leaf LARGE-COMMUNITY-LIST_NUMBER {
                    type union {
                        type int32;
                        type string;
                    }
                }                  //<(1-500)|LCOMMUNITY_LIST_NAME>
                leaf regexp {
                    type enumeration {
                        enum regexp;
                    }
                }                  //regexp
                leaf REGULAR_EXPRESSION {
                    type string;
                }                  //REGEX
                leaf statistics {
                    type enumeration {
                        enum statistics;
                    }
                }                  //statistics
                leaf statistics_json {
                    type enumeration {
                        enum statistics_json;
                    }
                }                  //json
                leaf BGP_PATH_SELECTION {
                    type enumeration {
                        enum bestpath;
                        enum multipath;
                    }
                }                  //<bestpath|multipath> ['Display only the bestpath', 'Display only multipaths']
                leaf RPKI_VALIDATION_STATE {
                    type enumeration {
                        enum valid;
                        enum invalid;
                        enum notfound;
                    }
                }                  //<valid|invalid|notfound> ['A valid path as determined by rpki', 'A invalid path as determined by rpki', 'A path that has no rpki data']
                leaf unicast {
                    type enumeration {
                        enum unicast;
                    }
                }                  //unicast
                leaf unicast_community-list {
                    type enumeration {
                        enum unicast_community-list;
                    }
                }                  //community-list
                leaf unicast_filter-list {
                    type enumeration {
                        enum unicast_filter-list;
                    }
                }                  //filter-list
                leaf unicast_prefix-list {
                    type enumeration {
                        enum unicast_prefix-list;
                    }
                }                  //prefix-list
                leaf unicast_access-list {
                    type enumeration {
                        enum unicast_access-list;
                    }
                }                  //access-list
                leaf unicast_route-map {
                    type enumeration {
                        enum unicast_route-map;
                    }
                }                  //route-map
                leaf unicast_rpki {
                    type enumeration {
                        enum unicast_rpki;
                    }
                }                  //rpki
                leaf unicast_version {
                    type enumeration {
                        enum unicast_version;
                    }
                }                  //version
                leaf unicast_alias {
                    type enumeration {
                        enum unicast_alias;
                    }
                }                  //alias
                leaf unicast_wide {
                    type enumeration {
                        enum unicast_wide;
                    }
                }                  //wide
                leaf unicast_neighbors {
                    type enumeration {
                        enum unicast_neighbors;
                    }
                }                  //neighbors
                leaf unicast_large-community-list {
                    type enumeration {
                        enum unicast_large-community-list;
                    }
                }                  //large-community-list
                leaf unicast_regexp {
                    type enumeration {
                        enum unicast_regexp;
                    }
                }                  //regexp
                leaf flowspec {
                    type enumeration {
                        enum flowspec;
                    }
                }                  //flowspec
                leaf flowspec_community-list {
                    type enumeration {
                        enum flowspec_community-list;
                    }
                }                  //community-list
                leaf flowspec_filter-list {
                    type enumeration {
                        enum flowspec_filter-list;
                    }
                }                  //filter-list
                leaf flowspec_prefix-list {
                    type enumeration {
                        enum flowspec_prefix-list;
                    }
                }                  //prefix-list
                leaf flowspec_access-list {
                    type enumeration {
                        enum flowspec_access-list;
                    }
                }                  //access-list
                leaf flowspec_route-map {
                    type enumeration {
                        enum flowspec_route-map;
                    }
                }                  //route-map
                leaf flowspec_rpki {
                    type enumeration {
                        enum flowspec_rpki;
                    }
                }                  //rpki
                leaf flowspec_version {
                    type enumeration {
                        enum flowspec_version;
                    }
                }                  //version
                leaf flowspec_alias {
                    type enumeration {
                        enum flowspec_alias;
                    }
                }                  //alias
                leaf flowspec_wide {
                    type enumeration {
                        enum flowspec_wide;
                    }
                }                  //wide
                leaf flowspec_neighbors {
                    type enumeration {
                        enum flowspec_neighbors;
                    }
                }                  //neighbors
                leaf flowspec_large-community-list {
                    type enumeration {
                        enum flowspec_large-community-list;
                    }
                }                  //large-community-list
                leaf flowspec_regexp {
                    type enumeration {
                        enum flowspec_regexp;
                    }
                }                  //regexp
                leaf all_cidr-only {
                    type enumeration {
                        enum all_cidr-only;
                    }
                }                  //all_cidr-only
                leaf all_cidr-only_wide {
                    type enumeration {
                        enum all_cidr-only_wide;
                    }
                }                  //wide
                leaf all_dampening {
                    type enumeration {
                        enum all_dampening;
                    }
                }                  //all_dampening
                leaf all_community {
                    type enumeration {
                        enum all_community;
                    }
                }                  //all_community
                leaf all_community_wide {
                    type enumeration {
                        enum all_community_wide;
                    }
                }                  //wide
                leaf all_detail-routes {
                    type enumeration {
                        enum all_detail-routes;
                    }
                }                  //all_detail-routes
                leaf all_detail-routes_wide {
                    type enumeration {
                        enum all_detail-routes_wide;
                    }
                }                  //wide
                leaf all_json {
                    type enumeration {
                        enum all_json;
                    }
                }                  //all_json
                leaf all_json_detail {
                    type enumeration {
                        enum all_json_detail;
                    }
                }                  //detail
                leaf all_summary {
                    type enumeration {
                        enum all_summary;
                    }
                }                  //all_summary
                leaf all_summary_neighbor {
                    type enumeration {
                        enum all_summary_neighbor;
                    }
                }                  //neighbor
                leaf all_summary_remote-as {
                    type enumeration {
                        enum all_summary_remote-as;
                    }
                }                  //remote-as
                leaf all_summary_json {
                    type enumeration {
                        enum all_summary_json;
                    }
                }                  //json
                leaf cidr-only_json {
                    type enumeration {
                        enum cidr-only_json;
                    }
                }                  //cidr-only_json
                leaf cidr-only_json_detail {
                    type enumeration {
                        enum cidr-only_json_detail;
                    }
                }                  //detail
                leaf dampening_parameters {
                    type enumeration {
                        enum dampening_parameters;
                    }
                }                  //dampening_parameters
                leaf dampening_parameters_json {
                    type enumeration {
                        enum dampening_parameters_json;
                    }
                }                  //json
                leaf community_local-AS {
                    type enumeration {
                        enum community_local-AS;
                    }
                }                  //community_local-AS
                leaf community_local-AS_wide {
                    type enumeration {
                        enum community_local-AS_wide;
                    }
                }                  //wide
                leaf community_no-advertise {
                    type enumeration {
                        enum community_no-advertise;
                    }
                }                  //community_no-advertise
                leaf community_no-advertise_wide {
                    type enumeration {
                        enum community_no-advertise_wide;
                    }
                }                  //wide
                leaf community_no-export {
                    type enumeration {
                        enum community_no-export;
                    }
                }                  //community_no-export
                leaf community_no-export_wide {
                    type enumeration {
                        enum community_no-export_wide;
                    }
                }                  //wide
                leaf community_graceful-shutdown {
                    type enumeration {
                        enum community_graceful-shutdown;
                    }
                }                  //community_graceful-shutdown
                leaf community_graceful-shutdown_wide {
                    type enumeration {
                        enum community_graceful-shutdown_wide;
                    }
                }                  //wide
                leaf community_no-peer {
                    type enumeration {
                        enum community_no-peer;
                    }
                }                  //community_no-peer
                leaf community_no-peer_wide {
                    type enumeration {
                        enum community_no-peer_wide;
                    }
                }                  //wide
                leaf community_blackhole {
                    type enumeration {
                        enum community_blackhole;
                    }
                }                  //community_blackhole
                leaf community_blackhole_wide {
                    type enumeration {
                        enum community_blackhole_wide;
                    }
                }                  //wide
                leaf community_llgr-stale {
                    type enumeration {
                        enum community_llgr-stale;
                    }
                }                  //community_llgr-stale
                leaf community_llgr-stale_wide {
                    type enumeration {
                        enum community_llgr-stale_wide;
                    }
                }                  //wide
                leaf community_no-llgr {
                    type enumeration {
                        enum community_no-llgr;
                    }
                }                  //community_no-llgr
                leaf community_no-llgr_wide {
                    type enumeration {
                        enum community_no-llgr_wide;
                    }
                }                  //wide
                leaf community_accept-own {
                    type enumeration {
                        enum community_accept-own;
                    }
                }                  //community_accept-own
                leaf community_accept-own_wide {
                    type enumeration {
                        enum community_accept-own_wide;
                    }
                }                  //wide
                leaf community_accept-own-nexthop {
                    type enumeration {
                        enum community_accept-own-nexthop;
                    }
                }                  //community_accept-own-nexthop
                leaf community_accept-own-nexthop_wide {
                    type enumeration {
                        enum community_accept-own-nexthop_wide;
                    }
                }                  //wide
                leaf community_route-filter-v6 {
                    type enumeration {
                        enum community_route-filter-v6;
                    }
                }                  //community_route-filter-v6
                leaf community_route-filter-v6_wide {
                    type enumeration {
                        enum community_route-filter-v6_wide;
                    }
                }                  //wide
                leaf community_route-filter-v4 {
                    type enumeration {
                        enum community_route-filter-v4;
                    }
                }                  //community_route-filter-v4
                leaf community_route-filter-v4_wide {
                    type enumeration {
                        enum community_route-filter-v4_wide;
                    }
                }                  //wide
                leaf community_route-filter-translated-v6 {
                    type enumeration {
                        enum community_route-filter-translated-v6;
                    }
                }                  //community_route-filter-translated-v6
                leaf community_route-filter-translated-v6_wide {
                    type enumeration {
                        enum community_route-filter-translated-v6_wide;
                    }
                }                  //wide
                leaf community_route-filter-translated-v4 {
                    type enumeration {
                        enum community_route-filter-translated-v4;
                    }
                }                  //community_route-filter-translated-v4
                leaf community_route-filter-translated-v4_wide {
                    type enumeration {
                        enum community_route-filter-translated-v4_wide;
                    }
                }                  //wide
                leaf community_exact-match {
                    type enumeration {
                        enum community_exact-match;
                    }
                }                  //community_exact-match
                leaf community_exact-match_wide {
                    type enumeration {
                        enum community_exact-match_wide;
                    }
                }                  //wide
                leaf community_json {
                    type enumeration {
                        enum community_json;
                    }
                }                  //community_json
                leaf community_json_detail {
                    type enumeration {
                        enum community_json_detail;
                    }
                }                  //detail
                leaf detail-routes_json {
                    type enumeration {
                        enum detail-routes_json;
                    }
                }                  //detail-routes_json
                leaf detail-routes_json_detail {
                    type enumeration {
                        enum detail-routes_json_detail;
                    }
                }                  //detail
                leaf summary_established {
                    type enumeration {
                        enum summary_established;
                    }
                }                  //summary_established
                leaf summary_established_neighbor {
                    type enumeration {
                        enum summary_established_neighbor;
                    }
                }                  //neighbor
                leaf summary_established_remote-as {
                    type enumeration {
                        enum summary_established_remote-as;
                    }
                }                  //remote-as
                leaf summary_established_json {
                    type enumeration {
                        enum summary_established_json;
                    }
                }                  //json
                leaf summary_failed {
                    type enumeration {
                        enum summary_failed;
                    }
                }                  //summary_failed
                leaf summary_failed_neighbor {
                    type enumeration {
                        enum summary_failed_neighbor;
                    }
                }                  //neighbor
                leaf summary_failed_remote-as {
                    type enumeration {
                        enum summary_failed_remote-as;
                    }
                }                  //remote-as
                leaf summary_failed_json {
                    type enumeration {
                        enum summary_failed_json;
                    }
                }                  //json
                leaf summary_terse {
                    type enumeration {
                        enum summary_terse;
                    }
                }                  //summary_terse
                leaf summary_terse_json {
                    type enumeration {
                        enum summary_terse_json;
                    }
                }                  //json
                leaf summary_wide {
                    type enumeration {
                        enum summary_wide;
                    }
                }                  //summary_wide
                leaf summary_wide_json {
                    type enumeration {
                        enum summary_wide_json;
                    }
                }                  //json
                leaf all_cidr-only_json {
                    type enumeration {
                        enum all_cidr-only_json;
                    }
                }                  //all_cidr-only_json
                leaf all_cidr-only_json_detail {
                    type enumeration {
                        enum all_cidr-only_json_detail;
                    }
                }                  //detail
                leaf all_dampening_parameters {
                    type enumeration {
                        enum all_dampening_parameters;
                    }
                }                  //all_dampening_parameters
                leaf all_dampening_parameters_json {
                    type enumeration {
                        enum all_dampening_parameters_json;
                    }
                }                  //json
                leaf all_community_local-AS {
                    type enumeration {
                        enum all_community_local-AS;
                    }
                }                  //all_community_local-AS
                leaf all_community_local-AS_wide {
                    type enumeration {
                        enum all_community_local-AS_wide;
                    }
                }                  //wide
                leaf all_community_no-advertise {
                    type enumeration {
                        enum all_community_no-advertise;
                    }
                }                  //all_community_no-advertise
                leaf all_community_no-advertise_wide {
                    type enumeration {
                        enum all_community_no-advertise_wide;
                    }
                }                  //wide
                leaf all_community_no-export {
                    type enumeration {
                        enum all_community_no-export;
                    }
                }                  //all_community_no-export
                leaf all_community_no-export_wide {
                    type enumeration {
                        enum all_community_no-export_wide;
                    }
                }                  //wide
                leaf all_community_graceful-shutdown {
                    type enumeration {
                        enum all_community_graceful-shutdown;
                    }
                }                  //all_community_graceful-shutdown
                leaf all_community_graceful-shutdown_wide {
                    type enumeration {
                        enum all_community_graceful-shutdown_wide;
                    }
                }                  //wide
                leaf all_community_no-peer {
                    type enumeration {
                        enum all_community_no-peer;
                    }
                }                  //all_community_no-peer
                leaf all_community_no-peer_wide {
                    type enumeration {
                        enum all_community_no-peer_wide;
                    }
                }                  //wide
                leaf all_community_blackhole {
                    type enumeration {
                        enum all_community_blackhole;
                    }
                }                  //all_community_blackhole
                leaf all_community_blackhole_wide {
                    type enumeration {
                        enum all_community_blackhole_wide;
                    }
                }                  //wide
                leaf all_community_llgr-stale {
                    type enumeration {
                        enum all_community_llgr-stale;
                    }
                }                  //all_community_llgr-stale
                leaf all_community_llgr-stale_wide {
                    type enumeration {
                        enum all_community_llgr-stale_wide;
                    }
                }                  //wide
                leaf all_community_no-llgr {
                    type enumeration {
                        enum all_community_no-llgr;
                    }
                }                  //all_community_no-llgr
                leaf all_community_no-llgr_wide {
                    type enumeration {
                        enum all_community_no-llgr_wide;
                    }
                }                  //wide
                leaf all_community_accept-own {
                    type enumeration {
                        enum all_community_accept-own;
                    }
                }                  //all_community_accept-own
                leaf all_community_accept-own_wide {
                    type enumeration {
                        enum all_community_accept-own_wide;
                    }
                }                  //wide
                leaf all_community_accept-own-nexthop {
                    type enumeration {
                        enum all_community_accept-own-nexthop;
                    }
                }                  //all_community_accept-own-nexthop
                leaf all_community_accept-own-nexthop_wide {
                    type enumeration {
                        enum all_community_accept-own-nexthop_wide;
                    }
                }                  //wide
                leaf all_community_route-filter-v6 {
                    type enumeration {
                        enum all_community_route-filter-v6;
                    }
                }                  //all_community_route-filter-v6
                leaf all_community_route-filter-v6_wide {
                    type enumeration {
                        enum all_community_route-filter-v6_wide;
                    }
                }                  //wide
                leaf all_community_route-filter-v4 {
                    type enumeration {
                        enum all_community_route-filter-v4;
                    }
                }                  //all_community_route-filter-v4
                leaf all_community_route-filter-v4_wide {
                    type enumeration {
                        enum all_community_route-filter-v4_wide;
                    }
                }                  //wide
                leaf all_community_route-filter-translated-v6 {
                    type enumeration {
                        enum all_community_route-filter-translated-v6;
                    }
                }                  //all_community_route-filter-translated-v6
                leaf all_community_route-filter-translated-v6_wide {
                    type enumeration {
                        enum all_community_route-filter-translated-v6_wide;
                    }
                }                  //wide
                leaf all_community_route-filter-translated-v4 {
                    type enumeration {
                        enum all_community_route-filter-translated-v4;
                    }
                }                  //all_community_route-filter-translated-v4
                leaf all_community_route-filter-translated-v4_wide {
                    type enumeration {
                        enum all_community_route-filter-translated-v4_wide;
                    }
                }                  //wide
                leaf all_community_exact-match {
                    type enumeration {
                        enum all_community_exact-match;
                    }
                }                  //all_community_exact-match
                leaf all_community_exact-match_wide {
                    type enumeration {
                        enum all_community_exact-match_wide;
                    }
                }                  //wide
                leaf all_community_json {
                    type enumeration {
                        enum all_community_json;
                    }
                }                  //all_community_json
                leaf all_community_json_detail {
                    type enumeration {
                        enum all_community_json_detail;
                    }
                }                  //detail
                leaf all_detail-routes_json {
                    type enumeration {
                        enum all_detail-routes_json;
                    }
                }                  //all_detail-routes_json
                leaf all_detail-routes_json_detail {
                    type enumeration {
                        enum all_detail-routes_json_detail;
                    }
                }                  //detail
                leaf all_summary_established {
                    type enumeration {
                        enum all_summary_established;
                    }
                }                  //all_summary_established
                leaf all_summary_established_neighbor {
                    type enumeration {
                        enum all_summary_established_neighbor;
                    }
                }                  //neighbor
                leaf all_summary_established_remote-as {
                    type enumeration {
                        enum all_summary_established_remote-as;
                    }
                }                  //remote-as
                leaf all_summary_established_json {
                    type enumeration {
                        enum all_summary_established_json;
                    }
                }                  //json
                leaf all_summary_failed {
                    type enumeration {
                        enum all_summary_failed;
                    }
                }                  //all_summary_failed
                leaf all_summary_failed_neighbor {
                    type enumeration {
                        enum all_summary_failed_neighbor;
                    }
                }                  //neighbor
                leaf all_summary_failed_remote-as {
                    type enumeration {
                        enum all_summary_failed_remote-as;
                    }
                }                  //remote-as
                leaf all_summary_failed_json {
                    type enumeration {
                        enum all_summary_failed_json;
                    }
                }                  //json
                leaf all_summary_terse {
                    type enumeration {
                        enum all_summary_terse;
                    }
                }                  //all_summary_terse
                leaf all_summary_terse_json {
                    type enumeration {
                        enum all_summary_terse_json;
                    }
                }                  //json
                leaf all_summary_wide {
                    type enumeration {
                        enum all_summary_wide;
                    }
                }                  //all_summary_wide
                leaf all_summary_wide_json {
                    type enumeration {
                        enum all_summary_wide_json;
                    }
                }                  //json
                leaf community_local-AS_exact-match {
                    type enumeration {
                        enum community_local-AS_exact-match;
                    }
                }                  //community_local-AS_exact-match
                leaf community_local-AS_exact-match_wide {
                    type enumeration {
                        enum community_local-AS_exact-match_wide;
                    }
                }                  //wide
                leaf community_local-AS_json {
                    type enumeration {
                        enum community_local-AS_json;
                    }
                }                  //community_local-AS_json
                leaf community_local-AS_json_detail {
                    type enumeration {
                        enum community_local-AS_json_detail;
                    }
                }                  //detail
                leaf community_no-advertise_exact-match {
                    type enumeration {
                        enum community_no-advertise_exact-match;
                    }
                }                  //community_no-advertise_exact-match
                leaf community_no-advertise_exact-match_wide {
                    type enumeration {
                        enum community_no-advertise_exact-match_wide;
                    }
                }                  //wide
                leaf community_no-advertise_json {
                    type enumeration {
                        enum community_no-advertise_json;
                    }
                }                  //community_no-advertise_json
                leaf community_no-advertise_json_detail {
                    type enumeration {
                        enum community_no-advertise_json_detail;
                    }
                }                  //detail
                leaf community_no-export_exact-match {
                    type enumeration {
                        enum community_no-export_exact-match;
                    }
                }                  //community_no-export_exact-match
                leaf community_no-export_exact-match_wide {
                    type enumeration {
                        enum community_no-export_exact-match_wide;
                    }
                }                  //wide
                leaf community_no-export_json {
                    type enumeration {
                        enum community_no-export_json;
                    }
                }                  //community_no-export_json
                leaf community_no-export_json_detail {
                    type enumeration {
                        enum community_no-export_json_detail;
                    }
                }                  //detail
                leaf community_graceful-shutdown_exact-match {
                    type enumeration {
                        enum community_graceful-shutdown_exact-match;
                    }
                }                  //community_graceful-shutdown_exact-match
                leaf community_graceful-shutdown_exact-match_wide {
                    type enumeration {
                        enum community_graceful-shutdown_exact-match_wide;
                    }
                }                  //wide
                leaf community_graceful-shutdown_json {
                    type enumeration {
                        enum community_graceful-shutdown_json;
                    }
                }                  //community_graceful-shutdown_json
                leaf community_graceful-shutdown_json_detail {
                    type enumeration {
                        enum community_graceful-shutdown_json_detail;
                    }
                }                  //detail
                leaf community_no-peer_exact-match {
                    type enumeration {
                        enum community_no-peer_exact-match;
                    }
                }                  //community_no-peer_exact-match
                leaf community_no-peer_exact-match_wide {
                    type enumeration {
                        enum community_no-peer_exact-match_wide;
                    }
                }                  //wide
                leaf community_no-peer_json {
                    type enumeration {
                        enum community_no-peer_json;
                    }
                }                  //community_no-peer_json
                leaf community_no-peer_json_detail {
                    type enumeration {
                        enum community_no-peer_json_detail;
                    }
                }                  //detail
                leaf community_blackhole_exact-match {
                    type enumeration {
                        enum community_blackhole_exact-match;
                    }
                }                  //community_blackhole_exact-match
                leaf community_blackhole_exact-match_wide {
                    type enumeration {
                        enum community_blackhole_exact-match_wide;
                    }
                }                  //wide
                leaf community_blackhole_json {
                    type enumeration {
                        enum community_blackhole_json;
                    }
                }                  //community_blackhole_json
                leaf community_blackhole_json_detail {
                    type enumeration {
                        enum community_blackhole_json_detail;
                    }
                }                  //detail
                leaf community_llgr-stale_exact-match {
                    type enumeration {
                        enum community_llgr-stale_exact-match;
                    }
                }                  //community_llgr-stale_exact-match
                leaf community_llgr-stale_exact-match_wide {
                    type enumeration {
                        enum community_llgr-stale_exact-match_wide;
                    }
                }                  //wide
                leaf community_llgr-stale_json {
                    type enumeration {
                        enum community_llgr-stale_json;
                    }
                }                  //community_llgr-stale_json
                leaf community_llgr-stale_json_detail {
                    type enumeration {
                        enum community_llgr-stale_json_detail;
                    }
                }                  //detail
                leaf community_no-llgr_exact-match {
                    type enumeration {
                        enum community_no-llgr_exact-match;
                    }
                }                  //community_no-llgr_exact-match
                leaf community_no-llgr_exact-match_wide {
                    type enumeration {
                        enum community_no-llgr_exact-match_wide;
                    }
                }                  //wide
                leaf community_no-llgr_json {
                    type enumeration {
                        enum community_no-llgr_json;
                    }
                }                  //community_no-llgr_json
                leaf community_no-llgr_json_detail {
                    type enumeration {
                        enum community_no-llgr_json_detail;
                    }
                }                  //detail
                leaf community_accept-own_exact-match {
                    type enumeration {
                        enum community_accept-own_exact-match;
                    }
                }                  //community_accept-own_exact-match
                leaf community_accept-own_exact-match_wide {
                    type enumeration {
                        enum community_accept-own_exact-match_wide;
                    }
                }                  //wide
                leaf community_accept-own_json {
                    type enumeration {
                        enum community_accept-own_json;
                    }
                }                  //community_accept-own_json
                leaf community_accept-own_json_detail {
                    type enumeration {
                        enum community_accept-own_json_detail;
                    }
                }                  //detail
                leaf community_accept-own-nexthop_exact-match {
                    type enumeration {
                        enum community_accept-own-nexthop_exact-match;
                    }
                }                  //community_accept-own-nexthop_exact-match
                leaf community_accept-own-nexthop_exact-match_wide {
                    type enumeration {
                        enum community_accept-own-nexthop_exact-match_wide;
                    }
                }                  //wide
                leaf community_accept-own-nexthop_json {
                    type enumeration {
                        enum community_accept-own-nexthop_json;
                    }
                }                  //community_accept-own-nexthop_json
                leaf community_accept-own-nexthop_json_detail {
                    type enumeration {
                        enum community_accept-own-nexthop_json_detail;
                    }
                }                  //detail
                leaf community_route-filter-v6_exact-match {
                    type enumeration {
                        enum community_route-filter-v6_exact-match;
                    }
                }                  //community_route-filter-v6_exact-match
                leaf community_route-filter-v6_exact-match_wide {
                    type enumeration {
                        enum community_route-filter-v6_exact-match_wide;
                    }
                }                  //wide
                leaf community_route-filter-v6_json {
                    type enumeration {
                        enum community_route-filter-v6_json;
                    }
                }                  //community_route-filter-v6_json
                leaf community_route-filter-v6_json_detail {
                    type enumeration {
                        enum community_route-filter-v6_json_detail;
                    }
                }                  //detail
                leaf community_route-filter-v4_exact-match {
                    type enumeration {
                        enum community_route-filter-v4_exact-match;
                    }
                }                  //community_route-filter-v4_exact-match
                leaf community_route-filter-v4_exact-match_wide {
                    type enumeration {
                        enum community_route-filter-v4_exact-match_wide;
                    }
                }                  //wide
                leaf community_route-filter-v4_json {
                    type enumeration {
                        enum community_route-filter-v4_json;
                    }
                }                  //community_route-filter-v4_json
                leaf community_route-filter-v4_json_detail {
                    type enumeration {
                        enum community_route-filter-v4_json_detail;
                    }
                }                  //detail
                leaf community_route-filter-translated-v6_exact-match {
                    type enumeration {
                        enum community_route-filter-translated-v6_exact-match;
                    }
                }                  //community_route-filter-translated-v6_exact-match
                leaf community_route-filter-translated-v6_exact-match_wide {
                    type enumeration {
                        enum community_route-filter-translated-v6_exact-match_wide;
                    }
                }                  //wide
                leaf community_route-filter-translated-v6_json {
                    type enumeration {
                        enum community_route-filter-translated-v6_json;
                    }
                }                  //community_route-filter-translated-v6_json
                leaf community_route-filter-translated-v6_json_detail {
                    type enumeration {
                        enum community_route-filter-translated-v6_json_detail;
                    }
                }                  //detail
                leaf community_route-filter-translated-v4_exact-match {
                    type enumeration {
                        enum community_route-filter-translated-v4_exact-match;
                    }
                }                  //community_route-filter-translated-v4_exact-match
                leaf community_route-filter-translated-v4_exact-match_wide {
                    type enumeration {
                        enum community_route-filter-translated-v4_exact-match_wide;
                    }
                }                  //wide
                leaf community_route-filter-translated-v4_json {
                    type enumeration {
                        enum community_route-filter-translated-v4_json;
                    }
                }                  //community_route-filter-translated-v4_json
                leaf community_route-filter-translated-v4_json_detail {
                    type enumeration {
                        enum community_route-filter-translated-v4_json_detail;
                    }
                }                  //detail
                leaf community_exact-match_json {
                    type enumeration {
                        enum community_exact-match_json;
                    }
                }                  //community_exact-match_json
                leaf community_exact-match_json_detail {
                    type enumeration {
                        enum community_exact-match_json_detail;
                    }
                }                  //detail
                leaf summary_established_terse {
                    type enumeration {
                        enum summary_established_terse;
                    }
                }                  //summary_established_terse
                leaf summary_established_terse_json {
                    type enumeration {
                        enum summary_established_terse_json;
                    }
                }                  //json
                leaf summary_established_wide {
                    type enumeration {
                        enum summary_established_wide;
                    }
                }                  //summary_established_wide
                leaf summary_established_wide_json {
                    type enumeration {
                        enum summary_established_wide_json;
                    }
                }                  //json
                leaf summary_failed_terse {
                    type enumeration {
                        enum summary_failed_terse;
                    }
                }                  //summary_failed_terse
                leaf summary_failed_terse_json {
                    type enumeration {
                        enum summary_failed_terse_json;
                    }
                }                  //json
                leaf summary_failed_wide {
                    type enumeration {
                        enum summary_failed_wide;
                    }
                }                  //summary_failed_wide
                leaf summary_failed_wide_json {
                    type enumeration {
                        enum summary_failed_wide_json;
                    }
                }                  //json
                leaf summary_terse_wide {
                    type enumeration {
                        enum summary_terse_wide;
                    }
                }                  //summary_terse_wide
                leaf summary_terse_wide_json {
                    type enumeration {
                        enum summary_terse_wide_json;
                    }
                }                  //json
                leaf all_community_local-AS_exact-match {
                    type enumeration {
                        enum all_community_local-AS_exact-match;
                    }
                }                  //all_community_local-AS_exact-match
                leaf all_community_local-AS_exact-match_wide {
                    type enumeration {
                        enum all_community_local-AS_exact-match_wide;
                    }
                }                  //wide
                leaf all_community_local-AS_json {
                    type enumeration {
                        enum all_community_local-AS_json;
                    }
                }                  //all_community_local-AS_json
                leaf all_community_local-AS_json_detail {
                    type enumeration {
                        enum all_community_local-AS_json_detail;
                    }
                }                  //detail
                leaf all_community_no-advertise_exact-match {
                    type enumeration {
                        enum all_community_no-advertise_exact-match;
                    }
                }                  //all_community_no-advertise_exact-match
                leaf all_community_no-advertise_exact-match_wide {
                    type enumeration {
                        enum all_community_no-advertise_exact-match_wide;
                    }
                }                  //wide
                leaf all_community_no-advertise_json {
                    type enumeration {
                        enum all_community_no-advertise_json;
                    }
                }                  //all_community_no-advertise_json
                leaf all_community_no-advertise_json_detail {
                    type enumeration {
                        enum all_community_no-advertise_json_detail;
                    }
                }                  //detail
                leaf all_community_no-export_exact-match {
                    type enumeration {
                        enum all_community_no-export_exact-match;
                    }
                }                  //all_community_no-export_exact-match
                leaf all_community_no-export_exact-match_wide {
                    type enumeration {
                        enum all_community_no-export_exact-match_wide;
                    }
                }                  //wide
                leaf all_community_no-export_json {
                    type enumeration {
                        enum all_community_no-export_json;
                    }
                }                  //all_community_no-export_json
                leaf all_community_no-export_json_detail {
                    type enumeration {
                        enum all_community_no-export_json_detail;
                    }
                }                  //detail
                leaf all_community_graceful-shutdown_exact-match {
                    type enumeration {
                        enum all_community_graceful-shutdown_exact-match;
                    }
                }                  //all_community_graceful-shutdown_exact-match
                leaf all_community_graceful-shutdown_exact-match_wide {
                    type enumeration {
                        enum all_community_graceful-shutdown_exact-match_wide;
                    }
                }                  //wide
                leaf all_community_graceful-shutdown_json {
                    type enumeration {
                        enum all_community_graceful-shutdown_json;
                    }
                }                  //all_community_graceful-shutdown_json
                leaf all_community_graceful-shutdown_json_detail {
                    type enumeration {
                        enum all_community_graceful-shutdown_json_detail;
                    }
                }                  //detail
                leaf all_community_no-peer_exact-match {
                    type enumeration {
                        enum all_community_no-peer_exact-match;
                    }
                }                  //all_community_no-peer_exact-match
                leaf all_community_no-peer_exact-match_wide {
                    type enumeration {
                        enum all_community_no-peer_exact-match_wide;
                    }
                }                  //wide
                leaf all_community_no-peer_json {
                    type enumeration {
                        enum all_community_no-peer_json;
                    }
                }                  //all_community_no-peer_json
                leaf all_community_no-peer_json_detail {
                    type enumeration {
                        enum all_community_no-peer_json_detail;
                    }
                }                  //detail
                leaf all_community_blackhole_exact-match {
                    type enumeration {
                        enum all_community_blackhole_exact-match;
                    }
                }                  //all_community_blackhole_exact-match
                leaf all_community_blackhole_exact-match_wide {
                    type enumeration {
                        enum all_community_blackhole_exact-match_wide;
                    }
                }                  //wide
                leaf all_community_blackhole_json {
                    type enumeration {
                        enum all_community_blackhole_json;
                    }
                }                  //all_community_blackhole_json
                leaf all_community_blackhole_json_detail {
                    type enumeration {
                        enum all_community_blackhole_json_detail;
                    }
                }                  //detail
                leaf all_community_llgr-stale_exact-match {
                    type enumeration {
                        enum all_community_llgr-stale_exact-match;
                    }
                }                  //all_community_llgr-stale_exact-match
                leaf all_community_llgr-stale_exact-match_wide {
                    type enumeration {
                        enum all_community_llgr-stale_exact-match_wide;
                    }
                }                  //wide
                leaf all_community_llgr-stale_json {
                    type enumeration {
                        enum all_community_llgr-stale_json;
                    }
                }                  //all_community_llgr-stale_json
                leaf all_community_llgr-stale_json_detail {
                    type enumeration {
                        enum all_community_llgr-stale_json_detail;
                    }
                }                  //detail
                leaf all_community_no-llgr_exact-match {
                    type enumeration {
                        enum all_community_no-llgr_exact-match;
                    }
                }                  //all_community_no-llgr_exact-match
                leaf all_community_no-llgr_exact-match_wide {
                    type enumeration {
                        enum all_community_no-llgr_exact-match_wide;
                    }
                }                  //wide
                leaf all_community_no-llgr_json {
                    type enumeration {
                        enum all_community_no-llgr_json;
                    }
                }                  //all_community_no-llgr_json
                leaf all_community_no-llgr_json_detail {
                    type enumeration {
                        enum all_community_no-llgr_json_detail;
                    }
                }                  //detail
                leaf all_community_accept-own_exact-match {
                    type enumeration {
                        enum all_community_accept-own_exact-match;
                    }
                }                  //all_community_accept-own_exact-match
                leaf all_community_accept-own_exact-match_wide {
                    type enumeration {
                        enum all_community_accept-own_exact-match_wide;
                    }
                }                  //wide
                leaf all_community_accept-own_json {
                    type enumeration {
                        enum all_community_accept-own_json;
                    }
                }                  //all_community_accept-own_json
                leaf all_community_accept-own_json_detail {
                    type enumeration {
                        enum all_community_accept-own_json_detail;
                    }
                }                  //detail
                leaf all_community_accept-own-nexthop_exact-match {
                    type enumeration {
                        enum all_community_accept-own-nexthop_exact-match;
                    }
                }                  //all_community_accept-own-nexthop_exact-match
                leaf all_community_accept-own-nexthop_exact-match_wide {
                    type enumeration {
                        enum all_community_accept-own-nexthop_exact-match_wide;
                    }
                }                  //wide
                leaf all_community_accept-own-nexthop_json {
                    type enumeration {
                        enum all_community_accept-own-nexthop_json;
                    }
                }                  //all_community_accept-own-nexthop_json
                leaf all_community_accept-own-nexthop_json_detail {
                    type enumeration {
                        enum all_community_accept-own-nexthop_json_detail;
                    }
                }                  //detail
                leaf all_community_route-filter-v6_exact-match {
                    type enumeration {
                        enum all_community_route-filter-v6_exact-match;
                    }
                }                  //all_community_route-filter-v6_exact-match
                leaf all_community_route-filter-v6_exact-match_wide {
                    type enumeration {
                        enum all_community_route-filter-v6_exact-match_wide;
                    }
                }                  //wide
                leaf all_community_route-filter-v6_json {
                    type enumeration {
                        enum all_community_route-filter-v6_json;
                    }
                }                  //all_community_route-filter-v6_json
                leaf all_community_route-filter-v6_json_detail {
                    type enumeration {
                        enum all_community_route-filter-v6_json_detail;
                    }
                }                  //detail
                leaf all_community_route-filter-v4_exact-match {
                    type enumeration {
                        enum all_community_route-filter-v4_exact-match;
                    }
                }                  //all_community_route-filter-v4_exact-match
                leaf all_community_route-filter-v4_exact-match_wide {
                    type enumeration {
                        enum all_community_route-filter-v4_exact-match_wide;
                    }
                }                  //wide
                leaf all_community_route-filter-v4_json {
                    type enumeration {
                        enum all_community_route-filter-v4_json;
                    }
                }                  //all_community_route-filter-v4_json
                leaf all_community_route-filter-v4_json_detail {
                    type enumeration {
                        enum all_community_route-filter-v4_json_detail;
                    }
                }                  //detail
                leaf all_community_route-filter-translated-v6_exact-match {
                    type enumeration {
                        enum all_community_route-filter-translated-v6_exact-match;
                    }
                }                  //all_community_route-filter-translated-v6_exact-match
                leaf all_community_route-filter-translated-v6_exact-match_wide {
                    type enumeration {
                        enum all_community_route-filter-translated-v6_exact-match_wide;
                    }
                }                  //wide
                leaf all_community_route-filter-translated-v6_json {
                    type enumeration {
                        enum all_community_route-filter-translated-v6_json;
                    }
                }                  //all_community_route-filter-translated-v6_json
                leaf all_community_route-filter-translated-v6_json_detail {
                    type enumeration {
                        enum all_community_route-filter-translated-v6_json_detail;
                    }
                }                  //detail
                leaf all_community_route-filter-translated-v4_exact-match {
                    type enumeration {
                        enum all_community_route-filter-translated-v4_exact-match;
                    }
                }                  //all_community_route-filter-translated-v4_exact-match
                leaf all_community_route-filter-translated-v4_exact-match_wide {
                    type enumeration {
                        enum all_community_route-filter-translated-v4_exact-match_wide;
                    }
                }                  //wide
                leaf all_community_route-filter-translated-v4_json {
                    type enumeration {
                        enum all_community_route-filter-translated-v4_json;
                    }
                }                  //all_community_route-filter-translated-v4_json
                leaf all_community_route-filter-translated-v4_json_detail {
                    type enumeration {
                        enum all_community_route-filter-translated-v4_json_detail;
                    }
                }                  //detail
                leaf all_community_exact-match_json {
                    type enumeration {
                        enum all_community_exact-match_json;
                    }
                }                  //all_community_exact-match_json
                leaf all_community_exact-match_json_detail {
                    type enumeration {
                        enum all_community_exact-match_json_detail;
                    }
                }                  //detail
                leaf all_summary_established_terse {
                    type enumeration {
                        enum all_summary_established_terse;
                    }
                }                  //all_summary_established_terse
                leaf all_summary_established_terse_json {
                    type enumeration {
                        enum all_summary_established_terse_json;
                    }
                }                  //json
                leaf all_summary_established_wide {
                    type enumeration {
                        enum all_summary_established_wide;
                    }
                }                  //all_summary_established_wide
                leaf all_summary_established_wide_json {
                    type enumeration {
                        enum all_summary_established_wide_json;
                    }
                }                  //json
                leaf all_summary_failed_terse {
                    type enumeration {
                        enum all_summary_failed_terse;
                    }
                }                  //all_summary_failed_terse
                leaf all_summary_failed_terse_json {
                    type enumeration {
                        enum all_summary_failed_terse_json;
                    }
                }                  //json
                leaf all_summary_failed_wide {
                    type enumeration {
                        enum all_summary_failed_wide;
                    }
                }                  //all_summary_failed_wide
                leaf all_summary_failed_wide_json {
                    type enumeration {
                        enum all_summary_failed_wide_json;
                    }
                }                  //json
                leaf all_summary_terse_wide {
                    type enumeration {
                        enum all_summary_terse_wide;
                    }
                }                  //all_summary_terse_wide
                leaf all_summary_terse_wide_json {
                    type enumeration {
                        enum all_summary_terse_wide_json;
                    }
                }                  //json
                leaf community_local-AS_exact-match_json {
                    type enumeration {
                        enum community_local-AS_exact-match_json;
                    }
                }                  //community_local-AS_exact-match_json
                leaf community_local-AS_exact-match_json_detail {
                    type enumeration {
                        enum community_local-AS_exact-match_json_detail;
                    }
                }                  //detail
                leaf community_no-advertise_exact-match_json {
                    type enumeration {
                        enum community_no-advertise_exact-match_json;
                    }
                }                  //community_no-advertise_exact-match_json
                leaf community_no-advertise_exact-match_json_detail {
                    type enumeration {
                        enum community_no-advertise_exact-match_json_detail;
                    }
                }                  //detail
                leaf community_no-export_exact-match_json {
                    type enumeration {
                        enum community_no-export_exact-match_json;
                    }
                }                  //community_no-export_exact-match_json
                leaf community_no-export_exact-match_json_detail {
                    type enumeration {
                        enum community_no-export_exact-match_json_detail;
                    }
                }                  //detail
                leaf community_graceful-shutdown_exact-match_json {
                    type enumeration {
                        enum community_graceful-shutdown_exact-match_json;
                    }
                }                  //community_graceful-shutdown_exact-match_json
                leaf community_graceful-shutdown_exact-match_json_detail {
                    type enumeration {
                        enum community_graceful-shutdown_exact-match_json_detail;
                    }
                }                  //detail
                leaf community_no-peer_exact-match_json {
                    type enumeration {
                        enum community_no-peer_exact-match_json;
                    }
                }                  //community_no-peer_exact-match_json
                leaf community_no-peer_exact-match_json_detail {
                    type enumeration {
                        enum community_no-peer_exact-match_json_detail;
                    }
                }                  //detail
                leaf community_blackhole_exact-match_json {
                    type enumeration {
                        enum community_blackhole_exact-match_json;
                    }
                }                  //community_blackhole_exact-match_json
                leaf community_blackhole_exact-match_json_detail {
                    type enumeration {
                        enum community_blackhole_exact-match_json_detail;
                    }
                }                  //detail
                leaf community_llgr-stale_exact-match_json {
                    type enumeration {
                        enum community_llgr-stale_exact-match_json;
                    }
                }                  //community_llgr-stale_exact-match_json
                leaf community_llgr-stale_exact-match_json_detail {
                    type enumeration {
                        enum community_llgr-stale_exact-match_json_detail;
                    }
                }                  //detail
                leaf community_no-llgr_exact-match_json {
                    type enumeration {
                        enum community_no-llgr_exact-match_json;
                    }
                }                  //community_no-llgr_exact-match_json
                leaf community_no-llgr_exact-match_json_detail {
                    type enumeration {
                        enum community_no-llgr_exact-match_json_detail;
                    }
                }                  //detail
                leaf community_accept-own_exact-match_json {
                    type enumeration {
                        enum community_accept-own_exact-match_json;
                    }
                }                  //community_accept-own_exact-match_json
                leaf community_accept-own_exact-match_json_detail {
                    type enumeration {
                        enum community_accept-own_exact-match_json_detail;
                    }
                }                  //detail
                leaf community_accept-own-nexthop_exact-match_json {
                    type enumeration {
                        enum community_accept-own-nexthop_exact-match_json;
                    }
                }                  //community_accept-own-nexthop_exact-match_json
                leaf community_accept-own-nexthop_exact-match_json_detail {
                    type enumeration {
                        enum community_accept-own-nexthop_exact-match_json_detail;
                    }
                }                  //detail
                leaf community_route-filter-v6_exact-match_json {
                    type enumeration {
                        enum community_route-filter-v6_exact-match_json;
                    }
                }                  //community_route-filter-v6_exact-match_json
                leaf community_route-filter-v6_exact-match_json_detail {
                    type enumeration {
                        enum community_route-filter-v6_exact-match_json_detail;
                    }
                }                  //detail
                leaf community_route-filter-v4_exact-match_json {
                    type enumeration {
                        enum community_route-filter-v4_exact-match_json;
                    }
                }                  //community_route-filter-v4_exact-match_json
                leaf community_route-filter-v4_exact-match_json_detail {
                    type enumeration {
                        enum community_route-filter-v4_exact-match_json_detail;
                    }
                }                  //detail
                leaf community_route-filter-translated-v6_exact-match_json {
                    type enumeration {
                        enum community_route-filter-translated-v6_exact-match_json;
                    }
                }                  //community_route-filter-translated-v6_exact-match_json
                leaf community_route-filter-translated-v6_exact-match_json_detail {
                    type enumeration {
                        enum community_route-filter-translated-v6_exact-match_json_detail;
                    }
                }                  //detail
                leaf community_route-filter-translated-v4_exact-match_json {
                    type enumeration {
                        enum community_route-filter-translated-v4_exact-match_json;
                    }
                }                  //community_route-filter-translated-v4_exact-match_json
                leaf community_route-filter-translated-v4_exact-match_json_detail {
                    type enumeration {
                        enum community_route-filter-translated-v4_exact-match_json_detail;
                    }
                }                  //detail
                leaf summary_established_terse_wide {
                    type enumeration {
                        enum summary_established_terse_wide;
                    }
                }                  //summary_established_terse_wide
                leaf summary_established_terse_wide_json {
                    type enumeration {
                        enum summary_established_terse_wide_json;
                    }
                }                  //json
                leaf summary_failed_terse_wide {
                    type enumeration {
                        enum summary_failed_terse_wide;
                    }
                }                  //summary_failed_terse_wide
                leaf summary_failed_terse_wide_json {
                    type enumeration {
                        enum summary_failed_terse_wide_json;
                    }
                }                  //json
                leaf all_community_local-AS_exact-match_json {
                    type enumeration {
                        enum all_community_local-AS_exact-match_json;
                    }
                }                  //all_community_local-AS_exact-match_json
                leaf all_community_local-AS_exact-match_json_detail {
                    type enumeration {
                        enum all_community_local-AS_exact-match_json_detail;
                    }
                }                  //detail
                leaf all_community_no-advertise_exact-match_json {
                    type enumeration {
                        enum all_community_no-advertise_exact-match_json;
                    }
                }                  //all_community_no-advertise_exact-match_json
                leaf all_community_no-advertise_exact-match_json_detail {
                    type enumeration {
                        enum all_community_no-advertise_exact-match_json_detail;
                    }
                }                  //detail
                leaf all_community_no-export_exact-match_json {
                    type enumeration {
                        enum all_community_no-export_exact-match_json;
                    }
                }                  //all_community_no-export_exact-match_json
                leaf all_community_no-export_exact-match_json_detail {
                    type enumeration {
                        enum all_community_no-export_exact-match_json_detail;
                    }
                }                  //detail
                leaf all_community_graceful-shutdown_exact-match_json {
                    type enumeration {
                        enum all_community_graceful-shutdown_exact-match_json;
                    }
                }                  //all_community_graceful-shutdown_exact-match_json
                leaf all_community_graceful-shutdown_exact-match_json_detail {
                    type enumeration {
                        enum all_community_graceful-shutdown_exact-match_json_detail;
                    }
                }                  //detail
                leaf all_community_no-peer_exact-match_json {
                    type enumeration {
                        enum all_community_no-peer_exact-match_json;
                    }
                }                  //all_community_no-peer_exact-match_json
                leaf all_community_no-peer_exact-match_json_detail {
                    type enumeration {
                        enum all_community_no-peer_exact-match_json_detail;
                    }
                }                  //detail
                leaf all_community_blackhole_exact-match_json {
                    type enumeration {
                        enum all_community_blackhole_exact-match_json;
                    }
                }                  //all_community_blackhole_exact-match_json
                leaf all_community_blackhole_exact-match_json_detail {
                    type enumeration {
                        enum all_community_blackhole_exact-match_json_detail;
                    }
                }                  //detail
                leaf all_community_llgr-stale_exact-match_json {
                    type enumeration {
                        enum all_community_llgr-stale_exact-match_json;
                    }
                }                  //all_community_llgr-stale_exact-match_json
                leaf all_community_llgr-stale_exact-match_json_detail {
                    type enumeration {
                        enum all_community_llgr-stale_exact-match_json_detail;
                    }
                }                  //detail
                leaf all_community_no-llgr_exact-match_json {
                    type enumeration {
                        enum all_community_no-llgr_exact-match_json;
                    }
                }                  //all_community_no-llgr_exact-match_json
                leaf all_community_no-llgr_exact-match_json_detail {
                    type enumeration {
                        enum all_community_no-llgr_exact-match_json_detail;
                    }
                }                  //detail
                leaf all_community_accept-own_exact-match_json {
                    type enumeration {
                        enum all_community_accept-own_exact-match_json;
                    }
                }                  //all_community_accept-own_exact-match_json
                leaf all_community_accept-own_exact-match_json_detail {
                    type enumeration {
                        enum all_community_accept-own_exact-match_json_detail;
                    }
                }                  //detail
                leaf all_community_accept-own-nexthop_exact-match_json {
                    type enumeration {
                        enum all_community_accept-own-nexthop_exact-match_json;
                    }
                }                  //all_community_accept-own-nexthop_exact-match_json
                leaf all_community_accept-own-nexthop_exact-match_json_detail {
                    type enumeration {
                        enum all_community_accept-own-nexthop_exact-match_json_detail;
                    }
                }                  //detail
                leaf all_community_route-filter-v6_exact-match_json {
                    type enumeration {
                        enum all_community_route-filter-v6_exact-match_json;
                    }
                }                  //all_community_route-filter-v6_exact-match_json
                leaf all_community_route-filter-v6_exact-match_json_detail {
                    type enumeration {
                        enum all_community_route-filter-v6_exact-match_json_detail;
                    }
                }                  //detail
                leaf all_community_route-filter-v4_exact-match_json {
                    type enumeration {
                        enum all_community_route-filter-v4_exact-match_json;
                    }
                }                  //all_community_route-filter-v4_exact-match_json
                leaf all_community_route-filter-v4_exact-match_json_detail {
                    type enumeration {
                        enum all_community_route-filter-v4_exact-match_json_detail;
                    }
                }                  //detail
                leaf all_community_route-filter-translated-v6_exact-match_json {
                    type enumeration {
                        enum all_community_route-filter-translated-v6_exact-match_json;
                    }
                }                  //all_community_route-filter-translated-v6_exact-match_json
                leaf all_community_route-filter-translated-v6_exact-match_json_detail {
                    type enumeration {
                        enum all_community_route-filter-translated-v6_exact-match_json_detail;
                    }
                }                  //detail
                leaf all_community_route-filter-translated-v4_exact-match_json {
                    type enumeration {
                        enum all_community_route-filter-translated-v4_exact-match_json;
                    }
                }                  //all_community_route-filter-translated-v4_exact-match_json
                leaf all_community_route-filter-translated-v4_exact-match_json_detail {
                    type enumeration {
                        enum all_community_route-filter-translated-v4_exact-match_json_detail;
                    }
                }                  //detail
                leaf all_summary_established_terse_wide {
                    type enumeration {
                        enum all_summary_established_terse_wide;
                    }
                }                  //all_summary_established_terse_wide
                leaf all_summary_established_terse_wide_json {
                    type enumeration {
                        enum all_summary_established_terse_wide_json;
                    }
                }                  //json
                leaf all_summary_failed_terse_wide {
                    type enumeration {
                        enum all_summary_failed_terse_wide;
                    }
                }                  //all_summary_failed_terse_wide
                leaf all_summary_failed_terse_wide_json {
                    type enumeration {
                        enum all_summary_failed_terse_wide_json;
                    }
                }                  //json
                leaf unicast_all {
                    type enumeration {
                        enum unicast_all;
                    }
                }                  //unicast_all
                leaf unicast_all_community-list {
                    type enumeration {
                        enum unicast_all_community-list;
                    }
                }                  //community-list
                leaf unicast_all_filter-list {
                    type enumeration {
                        enum unicast_all_filter-list;
                    }
                }                  //filter-list
                leaf unicast_all_prefix-list {
                    type enumeration {
                        enum unicast_all_prefix-list;
                    }
                }                  //prefix-list
                leaf unicast_all_access-list {
                    type enumeration {
                        enum unicast_all_access-list;
                    }
                }                  //access-list
                leaf unicast_all_route-map {
                    type enumeration {
                        enum unicast_all_route-map;
                    }
                }                  //route-map
                leaf unicast_all_rpki {
                    type enumeration {
                        enum unicast_all_rpki;
                    }
                }                  //rpki
                leaf unicast_all_version {
                    type enumeration {
                        enum unicast_all_version;
                    }
                }                  //version
                leaf unicast_all_alias {
                    type enumeration {
                        enum unicast_all_alias;
                    }
                }                  //alias
                leaf unicast_all_wide {
                    type enumeration {
                        enum unicast_all_wide;
                    }
                }                  //wide
                leaf unicast_all_neighbors {
                    type enumeration {
                        enum unicast_all_neighbors;
                    }
                }                  //neighbors
                leaf unicast_cidr-only {
                    type enumeration {
                        enum unicast_cidr-only;
                    }
                }                  //unicast_cidr-only
                leaf unicast_cidr-only_wide {
                    type enumeration {
                        enum unicast_cidr-only_wide;
                    }
                }                  //wide
                leaf unicast_dampening {
                    type enumeration {
                        enum unicast_dampening;
                    }
                }                  //unicast_dampening
                leaf unicast_community {
                    type enumeration {
                        enum unicast_community;
                    }
                }                  //unicast_community
                leaf unicast_community_wide {
                    type enumeration {
                        enum unicast_community_wide;
                    }
                }                  //wide
                leaf unicast_detail-routes {
                    type enumeration {
                        enum unicast_detail-routes;
                    }
                }                  //unicast_detail-routes
                leaf unicast_detail-routes_wide {
                    type enumeration {
                        enum unicast_detail-routes_wide;
                    }
                }                  //wide
                leaf unicast_json {
                    type enumeration {
                        enum unicast_json;
                    }
                }                  //unicast_json
                leaf unicast_json_detail {
                    type enumeration {
                        enum unicast_json_detail;
                    }
                }                  //detail
                leaf unicast_summary {
                    type enumeration {
                        enum unicast_summary;
                    }
                }                  //unicast_summary
                leaf unicast_summary_neighbor {
                    type enumeration {
                        enum unicast_summary_neighbor;
                    }
                }                  //neighbor
                leaf unicast_summary_remote-as {
                    type enumeration {
                        enum unicast_summary_remote-as;
                    }
                }                  //remote-as
                leaf unicast_summary_json {
                    type enumeration {
                        enum unicast_summary_json;
                    }
                }                  //json
                leaf unicast_large-community {
                    type enumeration {
                        enum unicast_large-community;
                    }
                }                  //unicast_large-community
                leaf unicast_large-community_json {
                    type enumeration {
                        enum unicast_large-community_json;
                    }
                }                  //json
                leaf unicast_statistics {
                    type enumeration {
                        enum unicast_statistics;
                    }
                }                  //unicast_statistics
                leaf unicast_statistics_json {
                    type enumeration {
                        enum unicast_statistics_json;
                    }
                }                  //json
                leaf unicast_update-groups {
                    type enumeration {
                        enum unicast_update-groups;
                    }
                }                  //unicast_update-groups
                leaf unicast_update-groups_json {
                    type enumeration {
                        enum unicast_update-groups_json;
                    }
                }                  //json
                leaf flowspec_all {
                    type enumeration {
                        enum flowspec_all;
                    }
                }                  //flowspec_all
                leaf flowspec_all_community-list {
                    type enumeration {
                        enum flowspec_all_community-list;
                    }
                }                  //community-list
                leaf flowspec_all_filter-list {
                    type enumeration {
                        enum flowspec_all_filter-list;
                    }
                }                  //filter-list
                leaf flowspec_all_prefix-list {
                    type enumeration {
                        enum flowspec_all_prefix-list;
                    }
                }                  //prefix-list
                leaf flowspec_all_access-list {
                    type enumeration {
                        enum flowspec_all_access-list;
                    }
                }                  //access-list
                leaf flowspec_all_route-map {
                    type enumeration {
                        enum flowspec_all_route-map;
                    }
                }                  //route-map
                leaf flowspec_all_rpki {
                    type enumeration {
                        enum flowspec_all_rpki;
                    }
                }                  //rpki
                leaf flowspec_all_version {
                    type enumeration {
                        enum flowspec_all_version;
                    }
                }                  //version
                leaf flowspec_all_alias {
                    type enumeration {
                        enum flowspec_all_alias;
                    }
                }                  //alias
                leaf flowspec_all_wide {
                    type enumeration {
                        enum flowspec_all_wide;
                    }
                }                  //wide
                leaf flowspec_all_neighbors {
                    type enumeration {
                        enum flowspec_all_neighbors;
                    }
                }                  //neighbors
                leaf flowspec_cidr-only {
                    type enumeration {
                        enum flowspec_cidr-only;
                    }
                }                  //flowspec_cidr-only
                leaf flowspec_cidr-only_wide {
                    type enumeration {
                        enum flowspec_cidr-only_wide;
                    }
                }                  //wide
                leaf flowspec_dampening {
                    type enumeration {
                        enum flowspec_dampening;
                    }
                }                  //flowspec_dampening
                leaf flowspec_community {
                    type enumeration {
                        enum flowspec_community;
                    }
                }                  //flowspec_community
                leaf flowspec_community_wide {
                    type enumeration {
                        enum flowspec_community_wide;
                    }
                }                  //wide
                leaf flowspec_detail-routes {
                    type enumeration {
                        enum flowspec_detail-routes;
                    }
                }                  //flowspec_detail-routes
                leaf flowspec_detail-routes_wide {
                    type enumeration {
                        enum flowspec_detail-routes_wide;
                    }
                }                  //wide
                leaf flowspec_json {
                    type enumeration {
                        enum flowspec_json;
                    }
                }                  //flowspec_json
                leaf flowspec_json_detail {
                    type enumeration {
                        enum flowspec_json_detail;
                    }
                }                  //detail
                leaf flowspec_summary {
                    type enumeration {
                        enum flowspec_summary;
                    }
                }                  //flowspec_summary
                leaf flowspec_summary_neighbor {
                    type enumeration {
                        enum flowspec_summary_neighbor;
                    }
                }                  //neighbor
                leaf flowspec_summary_remote-as {
                    type enumeration {
                        enum flowspec_summary_remote-as;
                    }
                }                  //remote-as
                leaf flowspec_summary_json {
                    type enumeration {
                        enum flowspec_summary_json;
                    }
                }                  //json
                leaf flowspec_large-community {
                    type enumeration {
                        enum flowspec_large-community;
                    }
                }                  //flowspec_large-community
                leaf flowspec_large-community_json {
                    type enumeration {
                        enum flowspec_large-community_json;
                    }
                }                  //json
                leaf flowspec_statistics {
                    type enumeration {
                        enum flowspec_statistics;
                    }
                }                  //flowspec_statistics
                leaf flowspec_statistics_json {
                    type enumeration {
                        enum flowspec_statistics_json;
                    }
                }                  //json
                leaf flowspec_update-groups {
                    type enumeration {
                        enum flowspec_update-groups;
                    }
                }                  //flowspec_update-groups
                leaf flowspec_update-groups_json {
                    type enumeration {
                        enum flowspec_update-groups_json;
                    }
                }                  //json
                leaf flowspec_detail {
                    type enumeration {
                        enum flowspec_detail;
                    }
                }                  //flowspec_detail
                leaf flowspec_detail_json {
                    type enumeration {
                        enum flowspec_detail_json;
                    }
                }                  //json
                leaf unicast_all_cidr-only {
                    type enumeration {
                        enum unicast_all_cidr-only;
                    }
                }                  //unicast_all_cidr-only
                leaf unicast_all_cidr-only_wide {
                    type enumeration {
                        enum unicast_all_cidr-only_wide;
                    }
                }                  //wide
                leaf unicast_all_dampening {
                    type enumeration {
                        enum unicast_all_dampening;
                    }
                }                  //unicast_all_dampening
                leaf unicast_all_community {
                    type enumeration {
                        enum unicast_all_community;
                    }
                }                  //unicast_all_community
                leaf unicast_all_community_wide {
                    type enumeration {
                        enum unicast_all_community_wide;
                    }
                }                  //wide
                leaf unicast_all_detail-routes {
                    type enumeration {
                        enum unicast_all_detail-routes;
                    }
                }                  //unicast_all_detail-routes
                leaf unicast_all_detail-routes_wide {
                    type enumeration {
                        enum unicast_all_detail-routes_wide;
                    }
                }                  //wide
                leaf unicast_all_json {
                    type enumeration {
                        enum unicast_all_json;
                    }
                }                  //unicast_all_json
                leaf unicast_all_json_detail {
                    type enumeration {
                        enum unicast_all_json_detail;
                    }
                }                  //detail
                leaf unicast_all_summary {
                    type enumeration {
                        enum unicast_all_summary;
                    }
                }                  //unicast_all_summary
                leaf unicast_all_summary_neighbor {
                    type enumeration {
                        enum unicast_all_summary_neighbor;
                    }
                }                  //neighbor
                leaf unicast_all_summary_remote-as {
                    type enumeration {
                        enum unicast_all_summary_remote-as;
                    }
                }                  //remote-as
                leaf unicast_all_summary_json {
                    type enumeration {
                        enum unicast_all_summary_json;
                    }
                }                  //json
                leaf unicast_cidr-only_json {
                    type enumeration {
                        enum unicast_cidr-only_json;
                    }
                }                  //unicast_cidr-only_json
                leaf unicast_cidr-only_json_detail {
                    type enumeration {
                        enum unicast_cidr-only_json_detail;
                    }
                }                  //detail
                leaf unicast_dampening_parameters {
                    type enumeration {
                        enum unicast_dampening_parameters;
                    }
                }                  //unicast_dampening_parameters
                leaf unicast_dampening_parameters_json {
                    type enumeration {
                        enum unicast_dampening_parameters_json;
                    }
                }                  //json
                leaf unicast_community_local-AS {
                    type enumeration {
                        enum unicast_community_local-AS;
                    }
                }                  //unicast_community_local-AS
                leaf unicast_community_local-AS_wide {
                    type enumeration {
                        enum unicast_community_local-AS_wide;
                    }
                }                  //wide
                leaf unicast_community_no-advertise {
                    type enumeration {
                        enum unicast_community_no-advertise;
                    }
                }                  //unicast_community_no-advertise
                leaf unicast_community_no-advertise_wide {
                    type enumeration {
                        enum unicast_community_no-advertise_wide;
                    }
                }                  //wide
                leaf unicast_community_no-export {
                    type enumeration {
                        enum unicast_community_no-export;
                    }
                }                  //unicast_community_no-export
                leaf unicast_community_no-export_wide {
                    type enumeration {
                        enum unicast_community_no-export_wide;
                    }
                }                  //wide
                leaf unicast_community_graceful-shutdown {
                    type enumeration {
                        enum unicast_community_graceful-shutdown;
                    }
                }                  //unicast_community_graceful-shutdown
                leaf unicast_community_graceful-shutdown_wide {
                    type enumeration {
                        enum unicast_community_graceful-shutdown_wide;
                    }
                }                  //wide
                leaf unicast_community_no-peer {
                    type enumeration {
                        enum unicast_community_no-peer;
                    }
                }                  //unicast_community_no-peer
                leaf unicast_community_no-peer_wide {
                    type enumeration {
                        enum unicast_community_no-peer_wide;
                    }
                }                  //wide
                leaf unicast_community_blackhole {
                    type enumeration {
                        enum unicast_community_blackhole;
                    }
                }                  //unicast_community_blackhole
                leaf unicast_community_blackhole_wide {
                    type enumeration {
                        enum unicast_community_blackhole_wide;
                    }
                }                  //wide
                leaf unicast_community_llgr-stale {
                    type enumeration {
                        enum unicast_community_llgr-stale;
                    }
                }                  //unicast_community_llgr-stale
                leaf unicast_community_llgr-stale_wide {
                    type enumeration {
                        enum unicast_community_llgr-stale_wide;
                    }
                }                  //wide
                leaf unicast_community_no-llgr {
                    type enumeration {
                        enum unicast_community_no-llgr;
                    }
                }                  //unicast_community_no-llgr
                leaf unicast_community_no-llgr_wide {
                    type enumeration {
                        enum unicast_community_no-llgr_wide;
                    }
                }                  //wide
                leaf unicast_community_accept-own {
                    type enumeration {
                        enum unicast_community_accept-own;
                    }
                }                  //unicast_community_accept-own
                leaf unicast_community_accept-own_wide {
                    type enumeration {
                        enum unicast_community_accept-own_wide;
                    }
                }                  //wide
                leaf unicast_community_accept-own-nexthop {
                    type enumeration {
                        enum unicast_community_accept-own-nexthop;
                    }
                }                  //unicast_community_accept-own-nexthop
                leaf unicast_community_accept-own-nexthop_wide {
                    type enumeration {
                        enum unicast_community_accept-own-nexthop_wide;
                    }
                }                  //wide
                leaf unicast_community_route-filter-v6 {
                    type enumeration {
                        enum unicast_community_route-filter-v6;
                    }
                }                  //unicast_community_route-filter-v6
                leaf unicast_community_route-filter-v6_wide {
                    type enumeration {
                        enum unicast_community_route-filter-v6_wide;
                    }
                }                  //wide
                leaf unicast_community_route-filter-v4 {
                    type enumeration {
                        enum unicast_community_route-filter-v4;
                    }
                }                  //unicast_community_route-filter-v4
                leaf unicast_community_route-filter-v4_wide {
                    type enumeration {
                        enum unicast_community_route-filter-v4_wide;
                    }
                }                  //wide
                leaf unicast_community_route-filter-translated-v6 {
                    type enumeration {
                        enum unicast_community_route-filter-translated-v6;
                    }
                }                  //unicast_community_route-filter-translated-v6
                leaf unicast_community_route-filter-translated-v6_wide {
                    type enumeration {
                        enum unicast_community_route-filter-translated-v6_wide;
                    }
                }                  //wide
                leaf unicast_community_route-filter-translated-v4 {
                    type enumeration {
                        enum unicast_community_route-filter-translated-v4;
                    }
                }                  //unicast_community_route-filter-translated-v4
                leaf unicast_community_route-filter-translated-v4_wide {
                    type enumeration {
                        enum unicast_community_route-filter-translated-v4_wide;
                    }
                }                  //wide
                leaf unicast_community_exact-match {
                    type enumeration {
                        enum unicast_community_exact-match;
                    }
                }                  //unicast_community_exact-match
                leaf unicast_community_exact-match_wide {
                    type enumeration {
                        enum unicast_community_exact-match_wide;
                    }
                }                  //wide
                leaf unicast_community_json {
                    type enumeration {
                        enum unicast_community_json;
                    }
                }                  //unicast_community_json
                leaf unicast_community_json_detail {
                    type enumeration {
                        enum unicast_community_json_detail;
                    }
                }                  //detail
                leaf unicast_detail-routes_json {
                    type enumeration {
                        enum unicast_detail-routes_json;
                    }
                }                  //unicast_detail-routes_json
                leaf unicast_detail-routes_json_detail {
                    type enumeration {
                        enum unicast_detail-routes_json_detail;
                    }
                }                  //detail
                leaf unicast_summary_established {
                    type enumeration {
                        enum unicast_summary_established;
                    }
                }                  //unicast_summary_established
                leaf unicast_summary_established_neighbor {
                    type enumeration {
                        enum unicast_summary_established_neighbor;
                    }
                }                  //neighbor
                leaf unicast_summary_established_remote-as {
                    type enumeration {
                        enum unicast_summary_established_remote-as;
                    }
                }                  //remote-as
                leaf unicast_summary_established_json {
                    type enumeration {
                        enum unicast_summary_established_json;
                    }
                }                  //json
                leaf unicast_summary_failed {
                    type enumeration {
                        enum unicast_summary_failed;
                    }
                }                  //unicast_summary_failed
                leaf unicast_summary_failed_neighbor {
                    type enumeration {
                        enum unicast_summary_failed_neighbor;
                    }
                }                  //neighbor
                leaf unicast_summary_failed_remote-as {
                    type enumeration {
                        enum unicast_summary_failed_remote-as;
                    }
                }                  //remote-as
                leaf unicast_summary_failed_json {
                    type enumeration {
                        enum unicast_summary_failed_json;
                    }
                }                  //json
                leaf unicast_summary_terse {
                    type enumeration {
                        enum unicast_summary_terse;
                    }
                }                  //unicast_summary_terse
                leaf unicast_summary_terse_json {
                    type enumeration {
                        enum unicast_summary_terse_json;
                    }
                }                  //json
                leaf unicast_summary_wide {
                    type enumeration {
                        enum unicast_summary_wide;
                    }
                }                  //unicast_summary_wide
                leaf unicast_summary_wide_json {
                    type enumeration {
                        enum unicast_summary_wide_json;
                    }
                }                  //json
                leaf flowspec_all_cidr-only {
                    type enumeration {
                        enum flowspec_all_cidr-only;
                    }
                }                  //flowspec_all_cidr-only
                leaf flowspec_all_cidr-only_wide {
                    type enumeration {
                        enum flowspec_all_cidr-only_wide;
                    }
                }                  //wide
                leaf flowspec_all_dampening {
                    type enumeration {
                        enum flowspec_all_dampening;
                    }
                }                  //flowspec_all_dampening
                leaf flowspec_all_community {
                    type enumeration {
                        enum flowspec_all_community;
                    }
                }                  //flowspec_all_community
                leaf flowspec_all_community_wide {
                    type enumeration {
                        enum flowspec_all_community_wide;
                    }
                }                  //wide
                leaf flowspec_all_detail-routes {
                    type enumeration {
                        enum flowspec_all_detail-routes;
                    }
                }                  //flowspec_all_detail-routes
                leaf flowspec_all_detail-routes_wide {
                    type enumeration {
                        enum flowspec_all_detail-routes_wide;
                    }
                }                  //wide
                leaf flowspec_all_json {
                    type enumeration {
                        enum flowspec_all_json;
                    }
                }                  //flowspec_all_json
                leaf flowspec_all_json_detail {
                    type enumeration {
                        enum flowspec_all_json_detail;
                    }
                }                  //detail
                leaf flowspec_all_summary {
                    type enumeration {
                        enum flowspec_all_summary;
                    }
                }                  //flowspec_all_summary
                leaf flowspec_all_summary_neighbor {
                    type enumeration {
                        enum flowspec_all_summary_neighbor;
                    }
                }                  //neighbor
                leaf flowspec_all_summary_remote-as {
                    type enumeration {
                        enum flowspec_all_summary_remote-as;
                    }
                }                  //remote-as
                leaf flowspec_all_summary_json {
                    type enumeration {
                        enum flowspec_all_summary_json;
                    }
                }                  //json
                leaf flowspec_cidr-only_json {
                    type enumeration {
                        enum flowspec_cidr-only_json;
                    }
                }                  //flowspec_cidr-only_json
                leaf flowspec_cidr-only_json_detail {
                    type enumeration {
                        enum flowspec_cidr-only_json_detail;
                    }
                }                  //detail
                leaf flowspec_dampening_parameters {
                    type enumeration {
                        enum flowspec_dampening_parameters;
                    }
                }                  //flowspec_dampening_parameters
                leaf flowspec_dampening_parameters_json {
                    type enumeration {
                        enum flowspec_dampening_parameters_json;
                    }
                }                  //json
                leaf flowspec_community_local-AS {
                    type enumeration {
                        enum flowspec_community_local-AS;
                    }
                }                  //flowspec_community_local-AS
                leaf flowspec_community_local-AS_wide {
                    type enumeration {
                        enum flowspec_community_local-AS_wide;
                    }
                }                  //wide
                leaf flowspec_community_no-advertise {
                    type enumeration {
                        enum flowspec_community_no-advertise;
                    }
                }                  //flowspec_community_no-advertise
                leaf flowspec_community_no-advertise_wide {
                    type enumeration {
                        enum flowspec_community_no-advertise_wide;
                    }
                }                  //wide
                leaf flowspec_community_no-export {
                    type enumeration {
                        enum flowspec_community_no-export;
                    }
                }                  //flowspec_community_no-export
                leaf flowspec_community_no-export_wide {
                    type enumeration {
                        enum flowspec_community_no-export_wide;
                    }
                }                  //wide
                leaf flowspec_community_graceful-shutdown {
                    type enumeration {
                        enum flowspec_community_graceful-shutdown;
                    }
                }                  //flowspec_community_graceful-shutdown
                leaf flowspec_community_graceful-shutdown_wide {
                    type enumeration {
                        enum flowspec_community_graceful-shutdown_wide;
                    }
                }                  //wide
                leaf flowspec_community_no-peer {
                    type enumeration {
                        enum flowspec_community_no-peer;
                    }
                }                  //flowspec_community_no-peer
                leaf flowspec_community_no-peer_wide {
                    type enumeration {
                        enum flowspec_community_no-peer_wide;
                    }
                }                  //wide
                leaf flowspec_community_blackhole {
                    type enumeration {
                        enum flowspec_community_blackhole;
                    }
                }                  //flowspec_community_blackhole
                leaf flowspec_community_blackhole_wide {
                    type enumeration {
                        enum flowspec_community_blackhole_wide;
                    }
                }                  //wide
                leaf flowspec_community_llgr-stale {
                    type enumeration {
                        enum flowspec_community_llgr-stale;
                    }
                }                  //flowspec_community_llgr-stale
                leaf flowspec_community_llgr-stale_wide {
                    type enumeration {
                        enum flowspec_community_llgr-stale_wide;
                    }
                }                  //wide
                leaf flowspec_community_no-llgr {
                    type enumeration {
                        enum flowspec_community_no-llgr;
                    }
                }                  //flowspec_community_no-llgr
                leaf flowspec_community_no-llgr_wide {
                    type enumeration {
                        enum flowspec_community_no-llgr_wide;
                    }
                }                  //wide
                leaf flowspec_community_accept-own {
                    type enumeration {
                        enum flowspec_community_accept-own;
                    }
                }                  //flowspec_community_accept-own
                leaf flowspec_community_accept-own_wide {
                    type enumeration {
                        enum flowspec_community_accept-own_wide;
                    }
                }                  //wide
                leaf flowspec_community_accept-own-nexthop {
                    type enumeration {
                        enum flowspec_community_accept-own-nexthop;
                    }
                }                  //flowspec_community_accept-own-nexthop
                leaf flowspec_community_accept-own-nexthop_wide {
                    type enumeration {
                        enum flowspec_community_accept-own-nexthop_wide;
                    }
                }                  //wide
                leaf flowspec_community_route-filter-v6 {
                    type enumeration {
                        enum flowspec_community_route-filter-v6;
                    }
                }                  //flowspec_community_route-filter-v6
                leaf flowspec_community_route-filter-v6_wide {
                    type enumeration {
                        enum flowspec_community_route-filter-v6_wide;
                    }
                }                  //wide
                leaf flowspec_community_route-filter-v4 {
                    type enumeration {
                        enum flowspec_community_route-filter-v4;
                    }
                }                  //flowspec_community_route-filter-v4
                leaf flowspec_community_route-filter-v4_wide {
                    type enumeration {
                        enum flowspec_community_route-filter-v4_wide;
                    }
                }                  //wide
                leaf flowspec_community_route-filter-translated-v6 {
                    type enumeration {
                        enum flowspec_community_route-filter-translated-v6;
                    }
                }                  //flowspec_community_route-filter-translated-v6
                leaf flowspec_community_route-filter-translated-v6_wide {
                    type enumeration {
                        enum flowspec_community_route-filter-translated-v6_wide;
                    }
                }                  //wide
                leaf flowspec_community_route-filter-translated-v4 {
                    type enumeration {
                        enum flowspec_community_route-filter-translated-v4;
                    }
                }                  //flowspec_community_route-filter-translated-v4
                leaf flowspec_community_route-filter-translated-v4_wide {
                    type enumeration {
                        enum flowspec_community_route-filter-translated-v4_wide;
                    }
                }                  //wide
                leaf flowspec_community_exact-match {
                    type enumeration {
                        enum flowspec_community_exact-match;
                    }
                }                  //flowspec_community_exact-match
                leaf flowspec_community_exact-match_wide {
                    type enumeration {
                        enum flowspec_community_exact-match_wide;
                    }
                }                  //wide
                leaf flowspec_community_json {
                    type enumeration {
                        enum flowspec_community_json;
                    }
                }                  //flowspec_community_json
                leaf flowspec_community_json_detail {
                    type enumeration {
                        enum flowspec_community_json_detail;
                    }
                }                  //detail
                leaf flowspec_detail-routes_json {
                    type enumeration {
                        enum flowspec_detail-routes_json;
                    }
                }                  //flowspec_detail-routes_json
                leaf flowspec_detail-routes_json_detail {
                    type enumeration {
                        enum flowspec_detail-routes_json_detail;
                    }
                }                  //detail
                leaf flowspec_summary_established {
                    type enumeration {
                        enum flowspec_summary_established;
                    }
                }                  //flowspec_summary_established
                leaf flowspec_summary_established_neighbor {
                    type enumeration {
                        enum flowspec_summary_established_neighbor;
                    }
                }                  //neighbor
                leaf flowspec_summary_established_remote-as {
                    type enumeration {
                        enum flowspec_summary_established_remote-as;
                    }
                }                  //remote-as
                leaf flowspec_summary_established_json {
                    type enumeration {
                        enum flowspec_summary_established_json;
                    }
                }                  //json
                leaf flowspec_summary_failed {
                    type enumeration {
                        enum flowspec_summary_failed;
                    }
                }                  //flowspec_summary_failed
                leaf flowspec_summary_failed_neighbor {
                    type enumeration {
                        enum flowspec_summary_failed_neighbor;
                    }
                }                  //neighbor
                leaf flowspec_summary_failed_remote-as {
                    type enumeration {
                        enum flowspec_summary_failed_remote-as;
                    }
                }                  //remote-as
                leaf flowspec_summary_failed_json {
                    type enumeration {
                        enum flowspec_summary_failed_json;
                    }
                }                  //json
                leaf flowspec_summary_terse {
                    type enumeration {
                        enum flowspec_summary_terse;
                    }
                }                  //flowspec_summary_terse
                leaf flowspec_summary_terse_json {
                    type enumeration {
                        enum flowspec_summary_terse_json;
                    }
                }                  //json
                leaf flowspec_summary_wide {
                    type enumeration {
                        enum flowspec_summary_wide;
                    }
                }                  //flowspec_summary_wide
                leaf flowspec_summary_wide_json {
                    type enumeration {
                        enum flowspec_summary_wide_json;
                    }
                }                  //json
                leaf unicast_all_cidr-only_json {
                    type enumeration {
                        enum unicast_all_cidr-only_json;
                    }
                }                  //unicast_all_cidr-only_json
                leaf unicast_all_cidr-only_json_detail {
                    type enumeration {
                        enum unicast_all_cidr-only_json_detail;
                    }
                }                  //detail
                leaf unicast_all_dampening_parameters {
                    type enumeration {
                        enum unicast_all_dampening_parameters;
                    }
                }                  //unicast_all_dampening_parameters
                leaf unicast_all_dampening_parameters_json {
                    type enumeration {
                        enum unicast_all_dampening_parameters_json;
                    }
                }                  //json
                leaf unicast_all_community_local-AS {
                    type enumeration {
                        enum unicast_all_community_local-AS;
                    }
                }                  //unicast_all_community_local-AS
                leaf unicast_all_community_local-AS_wide {
                    type enumeration {
                        enum unicast_all_community_local-AS_wide;
                    }
                }                  //wide
                leaf unicast_all_community_no-advertise {
                    type enumeration {
                        enum unicast_all_community_no-advertise;
                    }
                }                  //unicast_all_community_no-advertise
                leaf unicast_all_community_no-advertise_wide {
                    type enumeration {
                        enum unicast_all_community_no-advertise_wide;
                    }
                }                  //wide
                leaf unicast_all_community_no-export {
                    type enumeration {
                        enum unicast_all_community_no-export;
                    }
                }                  //unicast_all_community_no-export
                leaf unicast_all_community_no-export_wide {
                    type enumeration {
                        enum unicast_all_community_no-export_wide;
                    }
                }                  //wide
                leaf unicast_all_community_graceful-shutdown {
                    type enumeration {
                        enum unicast_all_community_graceful-shutdown;
                    }
                }                  //unicast_all_community_graceful-shutdown
                leaf unicast_all_community_graceful-shutdown_wide {
                    type enumeration {
                        enum unicast_all_community_graceful-shutdown_wide;
                    }
                }                  //wide
                leaf unicast_all_community_no-peer {
                    type enumeration {
                        enum unicast_all_community_no-peer;
                    }
                }                  //unicast_all_community_no-peer
                leaf unicast_all_community_no-peer_wide {
                    type enumeration {
                        enum unicast_all_community_no-peer_wide;
                    }
                }                  //wide
                leaf unicast_all_community_blackhole {
                    type enumeration {
                        enum unicast_all_community_blackhole;
                    }
                }                  //unicast_all_community_blackhole
                leaf unicast_all_community_blackhole_wide {
                    type enumeration {
                        enum unicast_all_community_blackhole_wide;
                    }
                }                  //wide
                leaf unicast_all_community_llgr-stale {
                    type enumeration {
                        enum unicast_all_community_llgr-stale;
                    }
                }                  //unicast_all_community_llgr-stale
                leaf unicast_all_community_llgr-stale_wide {
                    type enumeration {
                        enum unicast_all_community_llgr-stale_wide;
                    }
                }                  //wide
                leaf unicast_all_community_no-llgr {
                    type enumeration {
                        enum unicast_all_community_no-llgr;
                    }
                }                  //unicast_all_community_no-llgr
                leaf unicast_all_community_no-llgr_wide {
                    type enumeration {
                        enum unicast_all_community_no-llgr_wide;
                    }
                }                  //wide
                leaf unicast_all_community_accept-own {
                    type enumeration {
                        enum unicast_all_community_accept-own;
                    }
                }                  //unicast_all_community_accept-own
                leaf unicast_all_community_accept-own_wide {
                    type enumeration {
                        enum unicast_all_community_accept-own_wide;
                    }
                }                  //wide
                leaf unicast_all_community_accept-own-nexthop {
                    type enumeration {
                        enum unicast_all_community_accept-own-nexthop;
                    }
                }                  //unicast_all_community_accept-own-nexthop
                leaf unicast_all_community_accept-own-nexthop_wide {
                    type enumeration {
                        enum unicast_all_community_accept-own-nexthop_wide;
                    }
                }                  //wide
                leaf unicast_all_community_route-filter-v6 {
                    type enumeration {
                        enum unicast_all_community_route-filter-v6;
                    }
                }                  //unicast_all_community_route-filter-v6
                leaf unicast_all_community_route-filter-v6_wide {
                    type enumeration {
                        enum unicast_all_community_route-filter-v6_wide;
                    }
                }                  //wide
                leaf unicast_all_community_route-filter-v4 {
                    type enumeration {
                        enum unicast_all_community_route-filter-v4;
                    }
                }                  //unicast_all_community_route-filter-v4
                leaf unicast_all_community_route-filter-v4_wide {
                    type enumeration {
                        enum unicast_all_community_route-filter-v4_wide;
                    }
                }                  //wide
                leaf unicast_all_community_route-filter-translated-v6 {
                    type enumeration {
                        enum unicast_all_community_route-filter-translated-v6;
                    }
                }                  //unicast_all_community_route-filter-translated-v6
                leaf unicast_all_community_route-filter-translated-v6_wide {
                    type enumeration {
                        enum unicast_all_community_route-filter-translated-v6_wide;
                    }
                }                  //wide
                leaf unicast_all_community_route-filter-translated-v4 {
                    type enumeration {
                        enum unicast_all_community_route-filter-translated-v4;
                    }
                }                  //unicast_all_community_route-filter-translated-v4
                leaf unicast_all_community_route-filter-translated-v4_wide {
                    type enumeration {
                        enum unicast_all_community_route-filter-translated-v4_wide;
                    }
                }                  //wide
                leaf unicast_all_community_exact-match {
                    type enumeration {
                        enum unicast_all_community_exact-match;
                    }
                }                  //unicast_all_community_exact-match
                leaf unicast_all_community_exact-match_wide {
                    type enumeration {
                        enum unicast_all_community_exact-match_wide;
                    }
                }                  //wide
                leaf unicast_all_community_json {
                    type enumeration {
                        enum unicast_all_community_json;
                    }
                }                  //unicast_all_community_json
                leaf unicast_all_community_json_detail {
                    type enumeration {
                        enum unicast_all_community_json_detail;
                    }
                }                  //detail
                leaf unicast_all_detail-routes_json {
                    type enumeration {
                        enum unicast_all_detail-routes_json;
                    }
                }                  //unicast_all_detail-routes_json
                leaf unicast_all_detail-routes_json_detail {
                    type enumeration {
                        enum unicast_all_detail-routes_json_detail;
                    }
                }                  //detail
                leaf unicast_all_summary_established {
                    type enumeration {
                        enum unicast_all_summary_established;
                    }
                }                  //unicast_all_summary_established
                leaf unicast_all_summary_established_neighbor {
                    type enumeration {
                        enum unicast_all_summary_established_neighbor;
                    }
                }                  //neighbor
                leaf unicast_all_summary_established_remote-as {
                    type enumeration {
                        enum unicast_all_summary_established_remote-as;
                    }
                }                  //remote-as
                leaf unicast_all_summary_established_json {
                    type enumeration {
                        enum unicast_all_summary_established_json;
                    }
                }                  //json
                leaf unicast_all_summary_failed {
                    type enumeration {
                        enum unicast_all_summary_failed;
                    }
                }                  //unicast_all_summary_failed
                leaf unicast_all_summary_failed_neighbor {
                    type enumeration {
                        enum unicast_all_summary_failed_neighbor;
                    }
                }                  //neighbor
                leaf unicast_all_summary_failed_remote-as {
                    type enumeration {
                        enum unicast_all_summary_failed_remote-as;
                    }
                }                  //remote-as
                leaf unicast_all_summary_failed_json {
                    type enumeration {
                        enum unicast_all_summary_failed_json;
                    }
                }                  //json
                leaf unicast_all_summary_terse {
                    type enumeration {
                        enum unicast_all_summary_terse;
                    }
                }                  //unicast_all_summary_terse
                leaf unicast_all_summary_terse_json {
                    type enumeration {
                        enum unicast_all_summary_terse_json;
                    }
                }                  //json
                leaf unicast_all_summary_wide {
                    type enumeration {
                        enum unicast_all_summary_wide;
                    }
                }                  //unicast_all_summary_wide
                leaf unicast_all_summary_wide_json {
                    type enumeration {
                        enum unicast_all_summary_wide_json;
                    }
                }                  //json
                leaf unicast_community_local-AS_exact-match {
                    type enumeration {
                        enum unicast_community_local-AS_exact-match;
                    }
                }                  //unicast_community_local-AS_exact-match
                leaf unicast_community_local-AS_exact-match_wide {
                    type enumeration {
                        enum unicast_community_local-AS_exact-match_wide;
                    }
                }                  //wide
                leaf unicast_community_local-AS_json {
                    type enumeration {
                        enum unicast_community_local-AS_json;
                    }
                }                  //unicast_community_local-AS_json
                leaf unicast_community_local-AS_json_detail {
                    type enumeration {
                        enum unicast_community_local-AS_json_detail;
                    }
                }                  //detail
                leaf unicast_community_no-advertise_exact-match {
                    type enumeration {
                        enum unicast_community_no-advertise_exact-match;
                    }
                }                  //unicast_community_no-advertise_exact-match
                leaf unicast_community_no-advertise_exact-match_wide {
                    type enumeration {
                        enum unicast_community_no-advertise_exact-match_wide;
                    }
                }                  //wide
                leaf unicast_community_no-advertise_json {
                    type enumeration {
                        enum unicast_community_no-advertise_json;
                    }
                }                  //unicast_community_no-advertise_json
                leaf unicast_community_no-advertise_json_detail {
                    type enumeration {
                        enum unicast_community_no-advertise_json_detail;
                    }
                }                  //detail
                leaf unicast_community_no-export_exact-match {
                    type enumeration {
                        enum unicast_community_no-export_exact-match;
                    }
                }                  //unicast_community_no-export_exact-match
                leaf unicast_community_no-export_exact-match_wide {
                    type enumeration {
                        enum unicast_community_no-export_exact-match_wide;
                    }
                }                  //wide
                leaf unicast_community_no-export_json {
                    type enumeration {
                        enum unicast_community_no-export_json;
                    }
                }                  //unicast_community_no-export_json
                leaf unicast_community_no-export_json_detail {
                    type enumeration {
                        enum unicast_community_no-export_json_detail;
                    }
                }                  //detail
                leaf unicast_community_graceful-shutdown_exact-match {
                    type enumeration {
                        enum unicast_community_graceful-shutdown_exact-match;
                    }
                }                  //unicast_community_graceful-shutdown_exact-match
                leaf unicast_community_graceful-shutdown_exact-match_wide {
                    type enumeration {
                        enum unicast_community_graceful-shutdown_exact-match_wide;
                    }
                }                  //wide
                leaf unicast_community_graceful-shutdown_json {
                    type enumeration {
                        enum unicast_community_graceful-shutdown_json;
                    }
                }                  //unicast_community_graceful-shutdown_json
                leaf unicast_community_graceful-shutdown_json_detail {
                    type enumeration {
                        enum unicast_community_graceful-shutdown_json_detail;
                    }
                }                  //detail
                leaf unicast_community_no-peer_exact-match {
                    type enumeration {
                        enum unicast_community_no-peer_exact-match;
                    }
                }                  //unicast_community_no-peer_exact-match
                leaf unicast_community_no-peer_exact-match_wide {
                    type enumeration {
                        enum unicast_community_no-peer_exact-match_wide;
                    }
                }                  //wide
                leaf unicast_community_no-peer_json {
                    type enumeration {
                        enum unicast_community_no-peer_json;
                    }
                }                  //unicast_community_no-peer_json
                leaf unicast_community_no-peer_json_detail {
                    type enumeration {
                        enum unicast_community_no-peer_json_detail;
                    }
                }                  //detail
                leaf unicast_community_blackhole_exact-match {
                    type enumeration {
                        enum unicast_community_blackhole_exact-match;
                    }
                }                  //unicast_community_blackhole_exact-match
                leaf unicast_community_blackhole_exact-match_wide {
                    type enumeration {
                        enum unicast_community_blackhole_exact-match_wide;
                    }
                }                  //wide
                leaf unicast_community_blackhole_json {
                    type enumeration {
                        enum unicast_community_blackhole_json;
                    }
                }                  //unicast_community_blackhole_json
                leaf unicast_community_blackhole_json_detail {
                    type enumeration {
                        enum unicast_community_blackhole_json_detail;
                    }
                }                  //detail
                leaf unicast_community_llgr-stale_exact-match {
                    type enumeration {
                        enum unicast_community_llgr-stale_exact-match;
                    }
                }                  //unicast_community_llgr-stale_exact-match
                leaf unicast_community_llgr-stale_exact-match_wide {
                    type enumeration {
                        enum unicast_community_llgr-stale_exact-match_wide;
                    }
                }                  //wide
                leaf unicast_community_llgr-stale_json {
                    type enumeration {
                        enum unicast_community_llgr-stale_json;
                    }
                }                  //unicast_community_llgr-stale_json
                leaf unicast_community_llgr-stale_json_detail {
                    type enumeration {
                        enum unicast_community_llgr-stale_json_detail;
                    }
                }                  //detail
                leaf unicast_community_no-llgr_exact-match {
                    type enumeration {
                        enum unicast_community_no-llgr_exact-match;
                    }
                }                  //unicast_community_no-llgr_exact-match
                leaf unicast_community_no-llgr_exact-match_wide {
                    type enumeration {
                        enum unicast_community_no-llgr_exact-match_wide;
                    }
                }                  //wide
                leaf unicast_community_no-llgr_json {
                    type enumeration {
                        enum unicast_community_no-llgr_json;
                    }
                }                  //unicast_community_no-llgr_json
                leaf unicast_community_no-llgr_json_detail {
                    type enumeration {
                        enum unicast_community_no-llgr_json_detail;
                    }
                }                  //detail
                leaf unicast_community_accept-own_exact-match {
                    type enumeration {
                        enum unicast_community_accept-own_exact-match;
                    }
                }                  //unicast_community_accept-own_exact-match
                leaf unicast_community_accept-own_exact-match_wide {
                    type enumeration {
                        enum unicast_community_accept-own_exact-match_wide;
                    }
                }                  //wide
                leaf unicast_community_accept-own_json {
                    type enumeration {
                        enum unicast_community_accept-own_json;
                    }
                }                  //unicast_community_accept-own_json
                leaf unicast_community_accept-own_json_detail {
                    type enumeration {
                        enum unicast_community_accept-own_json_detail;
                    }
                }                  //detail
                leaf unicast_community_accept-own-nexthop_exact-match {
                    type enumeration {
                        enum unicast_community_accept-own-nexthop_exact-match;
                    }
                }                  //unicast_community_accept-own-nexthop_exact-match
                leaf unicast_community_accept-own-nexthop_exact-match_wide {
                    type enumeration {
                        enum unicast_community_accept-own-nexthop_exact-match_wide;
                    }
                }                  //wide
                leaf unicast_community_accept-own-nexthop_json {
                    type enumeration {
                        enum unicast_community_accept-own-nexthop_json;
                    }
                }                  //unicast_community_accept-own-nexthop_json
                leaf unicast_community_accept-own-nexthop_json_detail {
                    type enumeration {
                        enum unicast_community_accept-own-nexthop_json_detail;
                    }
                }                  //detail
                leaf unicast_community_route-filter-v6_exact-match {
                    type enumeration {
                        enum unicast_community_route-filter-v6_exact-match;
                    }
                }                  //unicast_community_route-filter-v6_exact-match
                leaf unicast_community_route-filter-v6_exact-match_wide {
                    type enumeration {
                        enum unicast_community_route-filter-v6_exact-match_wide;
                    }
                }                  //wide
                leaf unicast_community_route-filter-v6_json {
                    type enumeration {
                        enum unicast_community_route-filter-v6_json;
                    }
                }                  //unicast_community_route-filter-v6_json
                leaf unicast_community_route-filter-v6_json_detail {
                    type enumeration {
                        enum unicast_community_route-filter-v6_json_detail;
                    }
                }                  //detail
                leaf unicast_community_route-filter-v4_exact-match {
                    type enumeration {
                        enum unicast_community_route-filter-v4_exact-match;
                    }
                }                  //unicast_community_route-filter-v4_exact-match
                leaf unicast_community_route-filter-v4_exact-match_wide {
                    type enumeration {
                        enum unicast_community_route-filter-v4_exact-match_wide;
                    }
                }                  //wide
                leaf unicast_community_route-filter-v4_json {
                    type enumeration {
                        enum unicast_community_route-filter-v4_json;
                    }
                }                  //unicast_community_route-filter-v4_json
                leaf unicast_community_route-filter-v4_json_detail {
                    type enumeration {
                        enum unicast_community_route-filter-v4_json_detail;
                    }
                }                  //detail
                leaf unicast_community_route-filter-translated-v6_exact-match {
                    type enumeration {
                        enum unicast_community_route-filter-translated-v6_exact-match;
                    }
                }                  //unicast_community_route-filter-translated-v6_exact-match
                leaf unicast_community_route-filter-translated-v6_exact-match_wide {
                    type enumeration {
                        enum unicast_community_route-filter-translated-v6_exact-match_wide;
                    }
                }                  //wide
                leaf unicast_community_route-filter-translated-v6_json {
                    type enumeration {
                        enum unicast_community_route-filter-translated-v6_json;
                    }
                }                  //unicast_community_route-filter-translated-v6_json
                leaf unicast_community_route-filter-translated-v6_json_detail {
                    type enumeration {
                        enum unicast_community_route-filter-translated-v6_json_detail;
                    }
                }                  //detail
                leaf unicast_community_route-filter-translated-v4_exact-match {
                    type enumeration {
                        enum unicast_community_route-filter-translated-v4_exact-match;
                    }
                }                  //unicast_community_route-filter-translated-v4_exact-match
                leaf unicast_community_route-filter-translated-v4_exact-match_wide {
                    type enumeration {
                        enum unicast_community_route-filter-translated-v4_exact-match_wide;
                    }
                }                  //wide
                leaf unicast_community_route-filter-translated-v4_json {
                    type enumeration {
                        enum unicast_community_route-filter-translated-v4_json;
                    }
                }                  //unicast_community_route-filter-translated-v4_json
                leaf unicast_community_route-filter-translated-v4_json_detail {
                    type enumeration {
                        enum unicast_community_route-filter-translated-v4_json_detail;
                    }
                }                  //detail
                leaf unicast_community_exact-match_json {
                    type enumeration {
                        enum unicast_community_exact-match_json;
                    }
                }                  //unicast_community_exact-match_json
                leaf unicast_community_exact-match_json_detail {
                    type enumeration {
                        enum unicast_community_exact-match_json_detail;
                    }
                }                  //detail
                leaf unicast_summary_established_terse {
                    type enumeration {
                        enum unicast_summary_established_terse;
                    }
                }                  //unicast_summary_established_terse
                leaf unicast_summary_established_terse_json {
                    type enumeration {
                        enum unicast_summary_established_terse_json;
                    }
                }                  //json
                leaf unicast_summary_established_wide {
                    type enumeration {
                        enum unicast_summary_established_wide;
                    }
                }                  //unicast_summary_established_wide
                leaf unicast_summary_established_wide_json {
                    type enumeration {
                        enum unicast_summary_established_wide_json;
                    }
                }                  //json
                leaf unicast_summary_failed_terse {
                    type enumeration {
                        enum unicast_summary_failed_terse;
                    }
                }                  //unicast_summary_failed_terse
                leaf unicast_summary_failed_terse_json {
                    type enumeration {
                        enum unicast_summary_failed_terse_json;
                    }
                }                  //json
                leaf unicast_summary_failed_wide {
                    type enumeration {
                        enum unicast_summary_failed_wide;
                    }
                }                  //unicast_summary_failed_wide
                leaf unicast_summary_failed_wide_json {
                    type enumeration {
                        enum unicast_summary_failed_wide_json;
                    }
                }                  //json
                leaf unicast_summary_terse_wide {
                    type enumeration {
                        enum unicast_summary_terse_wide;
                    }
                }                  //unicast_summary_terse_wide
                leaf unicast_summary_terse_wide_json {
                    type enumeration {
                        enum unicast_summary_terse_wide_json;
                    }
                }                  //json
                leaf flowspec_all_cidr-only_json {
                    type enumeration {
                        enum flowspec_all_cidr-only_json;
                    }
                }                  //flowspec_all_cidr-only_json
                leaf flowspec_all_cidr-only_json_detail {
                    type enumeration {
                        enum flowspec_all_cidr-only_json_detail;
                    }
                }                  //detail
                leaf flowspec_all_dampening_parameters {
                    type enumeration {
                        enum flowspec_all_dampening_parameters;
                    }
                }                  //flowspec_all_dampening_parameters
                leaf flowspec_all_dampening_parameters_json {
                    type enumeration {
                        enum flowspec_all_dampening_parameters_json;
                    }
                }                  //json
                leaf flowspec_all_community_local-AS {
                    type enumeration {
                        enum flowspec_all_community_local-AS;
                    }
                }                  //flowspec_all_community_local-AS
                leaf flowspec_all_community_local-AS_wide {
                    type enumeration {
                        enum flowspec_all_community_local-AS_wide;
                    }
                }                  //wide
                leaf flowspec_all_community_no-advertise {
                    type enumeration {
                        enum flowspec_all_community_no-advertise;
                    }
                }                  //flowspec_all_community_no-advertise
                leaf flowspec_all_community_no-advertise_wide {
                    type enumeration {
                        enum flowspec_all_community_no-advertise_wide;
                    }
                }                  //wide
                leaf flowspec_all_community_no-export {
                    type enumeration {
                        enum flowspec_all_community_no-export;
                    }
                }                  //flowspec_all_community_no-export
                leaf flowspec_all_community_no-export_wide {
                    type enumeration {
                        enum flowspec_all_community_no-export_wide;
                    }
                }                  //wide
                leaf flowspec_all_community_graceful-shutdown {
                    type enumeration {
                        enum flowspec_all_community_graceful-shutdown;
                    }
                }                  //flowspec_all_community_graceful-shutdown
                leaf flowspec_all_community_graceful-shutdown_wide {
                    type enumeration {
                        enum flowspec_all_community_graceful-shutdown_wide;
                    }
                }                  //wide
                leaf flowspec_all_community_no-peer {
                    type enumeration {
                        enum flowspec_all_community_no-peer;
                    }
                }                  //flowspec_all_community_no-peer
                leaf flowspec_all_community_no-peer_wide {
                    type enumeration {
                        enum flowspec_all_community_no-peer_wide;
                    }
                }                  //wide
                leaf flowspec_all_community_blackhole {
                    type enumeration {
                        enum flowspec_all_community_blackhole;
                    }
                }                  //flowspec_all_community_blackhole
                leaf flowspec_all_community_blackhole_wide {
                    type enumeration {
                        enum flowspec_all_community_blackhole_wide;
                    }
                }                  //wide
                leaf flowspec_all_community_llgr-stale {
                    type enumeration {
                        enum flowspec_all_community_llgr-stale;
                    }
                }                  //flowspec_all_community_llgr-stale
                leaf flowspec_all_community_llgr-stale_wide {
                    type enumeration {
                        enum flowspec_all_community_llgr-stale_wide;
                    }
                }                  //wide
                leaf flowspec_all_community_no-llgr {
                    type enumeration {
                        enum flowspec_all_community_no-llgr;
                    }
                }                  //flowspec_all_community_no-llgr
                leaf flowspec_all_community_no-llgr_wide {
                    type enumeration {
                        enum flowspec_all_community_no-llgr_wide;
                    }
                }                  //wide
                leaf flowspec_all_community_accept-own {
                    type enumeration {
                        enum flowspec_all_community_accept-own;
                    }
                }                  //flowspec_all_community_accept-own
                leaf flowspec_all_community_accept-own_wide {
                    type enumeration {
                        enum flowspec_all_community_accept-own_wide;
                    }
                }                  //wide
                leaf flowspec_all_community_accept-own-nexthop {
                    type enumeration {
                        enum flowspec_all_community_accept-own-nexthop;
                    }
                }                  //flowspec_all_community_accept-own-nexthop
                leaf flowspec_all_community_accept-own-nexthop_wide {
                    type enumeration {
                        enum flowspec_all_community_accept-own-nexthop_wide;
                    }
                }                  //wide
                leaf flowspec_all_community_route-filter-v6 {
                    type enumeration {
                        enum flowspec_all_community_route-filter-v6;
                    }
                }                  //flowspec_all_community_route-filter-v6
                leaf flowspec_all_community_route-filter-v6_wide {
                    type enumeration {
                        enum flowspec_all_community_route-filter-v6_wide;
                    }
                }                  //wide
                leaf flowspec_all_community_route-filter-v4 {
                    type enumeration {
                        enum flowspec_all_community_route-filter-v4;
                    }
                }                  //flowspec_all_community_route-filter-v4
                leaf flowspec_all_community_route-filter-v4_wide {
                    type enumeration {
                        enum flowspec_all_community_route-filter-v4_wide;
                    }
                }                  //wide
                leaf flowspec_all_community_route-filter-translated-v6 {
                    type enumeration {
                        enum flowspec_all_community_route-filter-translated-v6;
                    }
                }                  //flowspec_all_community_route-filter-translated-v6
                leaf flowspec_all_community_route-filter-translated-v6_wide {
                    type enumeration {
                        enum flowspec_all_community_route-filter-translated-v6_wide;
                    }
                }                  //wide
                leaf flowspec_all_community_route-filter-translated-v4 {
                    type enumeration {
                        enum flowspec_all_community_route-filter-translated-v4;
                    }
                }                  //flowspec_all_community_route-filter-translated-v4
                leaf flowspec_all_community_route-filter-translated-v4_wide {
                    type enumeration {
                        enum flowspec_all_community_route-filter-translated-v4_wide;
                    }
                }                  //wide
                leaf flowspec_all_community_exact-match {
                    type enumeration {
                        enum flowspec_all_community_exact-match;
                    }
                }                  //flowspec_all_community_exact-match
                leaf flowspec_all_community_exact-match_wide {
                    type enumeration {
                        enum flowspec_all_community_exact-match_wide;
                    }
                }                  //wide
                leaf flowspec_all_community_json {
                    type enumeration {
                        enum flowspec_all_community_json;
                    }
                }                  //flowspec_all_community_json
                leaf flowspec_all_community_json_detail {
                    type enumeration {
                        enum flowspec_all_community_json_detail;
                    }
                }                  //detail
                leaf flowspec_all_detail-routes_json {
                    type enumeration {
                        enum flowspec_all_detail-routes_json;
                    }
                }                  //flowspec_all_detail-routes_json
                leaf flowspec_all_detail-routes_json_detail {
                    type enumeration {
                        enum flowspec_all_detail-routes_json_detail;
                    }
                }                  //detail
                leaf flowspec_all_summary_established {
                    type enumeration {
                        enum flowspec_all_summary_established;
                    }
                }                  //flowspec_all_summary_established
                leaf flowspec_all_summary_established_neighbor {
                    type enumeration {
                        enum flowspec_all_summary_established_neighbor;
                    }
                }                  //neighbor
                leaf flowspec_all_summary_established_remote-as {
                    type enumeration {
                        enum flowspec_all_summary_established_remote-as;
                    }
                }                  //remote-as
                leaf flowspec_all_summary_established_json {
                    type enumeration {
                        enum flowspec_all_summary_established_json;
                    }
                }                  //json
                leaf flowspec_all_summary_failed {
                    type enumeration {
                        enum flowspec_all_summary_failed;
                    }
                }                  //flowspec_all_summary_failed
                leaf flowspec_all_summary_failed_neighbor {
                    type enumeration {
                        enum flowspec_all_summary_failed_neighbor;
                    }
                }                  //neighbor
                leaf flowspec_all_summary_failed_remote-as {
                    type enumeration {
                        enum flowspec_all_summary_failed_remote-as;
                    }
                }                  //remote-as
                leaf flowspec_all_summary_failed_json {
                    type enumeration {
                        enum flowspec_all_summary_failed_json;
                    }
                }                  //json
                leaf flowspec_all_summary_terse {
                    type enumeration {
                        enum flowspec_all_summary_terse;
                    }
                }                  //flowspec_all_summary_terse
                leaf flowspec_all_summary_terse_json {
                    type enumeration {
                        enum flowspec_all_summary_terse_json;
                    }
                }                  //json
                leaf flowspec_all_summary_wide {
                    type enumeration {
                        enum flowspec_all_summary_wide;
                    }
                }                  //flowspec_all_summary_wide
                leaf flowspec_all_summary_wide_json {
                    type enumeration {
                        enum flowspec_all_summary_wide_json;
                    }
                }                  //json
                leaf flowspec_community_local-AS_exact-match {
                    type enumeration {
                        enum flowspec_community_local-AS_exact-match;
                    }
                }                  //flowspec_community_local-AS_exact-match
                leaf flowspec_community_local-AS_exact-match_wide {
                    type enumeration {
                        enum flowspec_community_local-AS_exact-match_wide;
                    }
                }                  //wide
                leaf flowspec_community_local-AS_json {
                    type enumeration {
                        enum flowspec_community_local-AS_json;
                    }
                }                  //flowspec_community_local-AS_json
                leaf flowspec_community_local-AS_json_detail {
                    type enumeration {
                        enum flowspec_community_local-AS_json_detail;
                    }
                }                  //detail
                leaf flowspec_community_no-advertise_exact-match {
                    type enumeration {
                        enum flowspec_community_no-advertise_exact-match;
                    }
                }                  //flowspec_community_no-advertise_exact-match
                leaf flowspec_community_no-advertise_exact-match_wide {
                    type enumeration {
                        enum flowspec_community_no-advertise_exact-match_wide;
                    }
                }                  //wide
                leaf flowspec_community_no-advertise_json {
                    type enumeration {
                        enum flowspec_community_no-advertise_json;
                    }
                }                  //flowspec_community_no-advertise_json
                leaf flowspec_community_no-advertise_json_detail {
                    type enumeration {
                        enum flowspec_community_no-advertise_json_detail;
                    }
                }                  //detail
                leaf flowspec_community_no-export_exact-match {
                    type enumeration {
                        enum flowspec_community_no-export_exact-match;
                    }
                }                  //flowspec_community_no-export_exact-match
                leaf flowspec_community_no-export_exact-match_wide {
                    type enumeration {
                        enum flowspec_community_no-export_exact-match_wide;
                    }
                }                  //wide
                leaf flowspec_community_no-export_json {
                    type enumeration {
                        enum flowspec_community_no-export_json;
                    }
                }                  //flowspec_community_no-export_json
                leaf flowspec_community_no-export_json_detail {
                    type enumeration {
                        enum flowspec_community_no-export_json_detail;
                    }
                }                  //detail
                leaf flowspec_community_graceful-shutdown_exact-match {
                    type enumeration {
                        enum flowspec_community_graceful-shutdown_exact-match;
                    }
                }                  //flowspec_community_graceful-shutdown_exact-match
                leaf flowspec_community_graceful-shutdown_exact-match_wide {
                    type enumeration {
                        enum flowspec_community_graceful-shutdown_exact-match_wide;
                    }
                }                  //wide
                leaf flowspec_community_graceful-shutdown_json {
                    type enumeration {
                        enum flowspec_community_graceful-shutdown_json;
                    }
                }                  //flowspec_community_graceful-shutdown_json
                leaf flowspec_community_graceful-shutdown_json_detail {
                    type enumeration {
                        enum flowspec_community_graceful-shutdown_json_detail;
                    }
                }                  //detail
                leaf flowspec_community_no-peer_exact-match {
                    type enumeration {
                        enum flowspec_community_no-peer_exact-match;
                    }
                }                  //flowspec_community_no-peer_exact-match
                leaf flowspec_community_no-peer_exact-match_wide {
                    type enumeration {
                        enum flowspec_community_no-peer_exact-match_wide;
                    }
                }                  //wide
                leaf flowspec_community_no-peer_json {
                    type enumeration {
                        enum flowspec_community_no-peer_json;
                    }
                }                  //flowspec_community_no-peer_json
                leaf flowspec_community_no-peer_json_detail {
                    type enumeration {
                        enum flowspec_community_no-peer_json_detail;
                    }
                }                  //detail
                leaf flowspec_community_blackhole_exact-match {
                    type enumeration {
                        enum flowspec_community_blackhole_exact-match;
                    }
                }                  //flowspec_community_blackhole_exact-match
                leaf flowspec_community_blackhole_exact-match_wide {
                    type enumeration {
                        enum flowspec_community_blackhole_exact-match_wide;
                    }
                }                  //wide
                leaf flowspec_community_blackhole_json {
                    type enumeration {
                        enum flowspec_community_blackhole_json;
                    }
                }                  //flowspec_community_blackhole_json
                leaf flowspec_community_blackhole_json_detail {
                    type enumeration {
                        enum flowspec_community_blackhole_json_detail;
                    }
                }                  //detail
                leaf flowspec_community_llgr-stale_exact-match {
                    type enumeration {
                        enum flowspec_community_llgr-stale_exact-match;
                    }
                }                  //flowspec_community_llgr-stale_exact-match
                leaf flowspec_community_llgr-stale_exact-match_wide {
                    type enumeration {
                        enum flowspec_community_llgr-stale_exact-match_wide;
                    }
                }                  //wide
                leaf flowspec_community_llgr-stale_json {
                    type enumeration {
                        enum flowspec_community_llgr-stale_json;
                    }
                }                  //flowspec_community_llgr-stale_json
                leaf flowspec_community_llgr-stale_json_detail {
                    type enumeration {
                        enum flowspec_community_llgr-stale_json_detail;
                    }
                }                  //detail
                leaf flowspec_community_no-llgr_exact-match {
                    type enumeration {
                        enum flowspec_community_no-llgr_exact-match;
                    }
                }                  //flowspec_community_no-llgr_exact-match
                leaf flowspec_community_no-llgr_exact-match_wide {
                    type enumeration {
                        enum flowspec_community_no-llgr_exact-match_wide;
                    }
                }                  //wide
                leaf flowspec_community_no-llgr_json {
                    type enumeration {
                        enum flowspec_community_no-llgr_json;
                    }
                }                  //flowspec_community_no-llgr_json
                leaf flowspec_community_no-llgr_json_detail {
                    type enumeration {
                        enum flowspec_community_no-llgr_json_detail;
                    }
                }                  //detail
                leaf flowspec_community_accept-own_exact-match {
                    type enumeration {
                        enum flowspec_community_accept-own_exact-match;
                    }
                }                  //flowspec_community_accept-own_exact-match
                leaf flowspec_community_accept-own_exact-match_wide {
                    type enumeration {
                        enum flowspec_community_accept-own_exact-match_wide;
                    }
                }                  //wide
                leaf flowspec_community_accept-own_json {
                    type enumeration {
                        enum flowspec_community_accept-own_json;
                    }
                }                  //flowspec_community_accept-own_json
                leaf flowspec_community_accept-own_json_detail {
                    type enumeration {
                        enum flowspec_community_accept-own_json_detail;
                    }
                }                  //detail
                leaf flowspec_community_accept-own-nexthop_exact-match {
                    type enumeration {
                        enum flowspec_community_accept-own-nexthop_exact-match;
                    }
                }                  //flowspec_community_accept-own-nexthop_exact-match
                leaf flowspec_community_accept-own-nexthop_exact-match_wide {
                    type enumeration {
                        enum flowspec_community_accept-own-nexthop_exact-match_wide;
                    }
                }                  //wide
                leaf flowspec_community_accept-own-nexthop_json {
                    type enumeration {
                        enum flowspec_community_accept-own-nexthop_json;
                    }
                }                  //flowspec_community_accept-own-nexthop_json
                leaf flowspec_community_accept-own-nexthop_json_detail {
                    type enumeration {
                        enum flowspec_community_accept-own-nexthop_json_detail;
                    }
                }                  //detail
                leaf flowspec_community_route-filter-v6_exact-match {
                    type enumeration {
                        enum flowspec_community_route-filter-v6_exact-match;
                    }
                }                  //flowspec_community_route-filter-v6_exact-match
                leaf flowspec_community_route-filter-v6_exact-match_wide {
                    type enumeration {
                        enum flowspec_community_route-filter-v6_exact-match_wide;
                    }
                }                  //wide
                leaf flowspec_community_route-filter-v6_json {
                    type enumeration {
                        enum flowspec_community_route-filter-v6_json;
                    }
                }                  //flowspec_community_route-filter-v6_json
                leaf flowspec_community_route-filter-v6_json_detail {
                    type enumeration {
                        enum flowspec_community_route-filter-v6_json_detail;
                    }
                }                  //detail
                leaf flowspec_community_route-filter-v4_exact-match {
                    type enumeration {
                        enum flowspec_community_route-filter-v4_exact-match;
                    }
                }                  //flowspec_community_route-filter-v4_exact-match
                leaf flowspec_community_route-filter-v4_exact-match_wide {
                    type enumeration {
                        enum flowspec_community_route-filter-v4_exact-match_wide;
                    }
                }                  //wide
                leaf flowspec_community_route-filter-v4_json {
                    type enumeration {
                        enum flowspec_community_route-filter-v4_json;
                    }
                }                  //flowspec_community_route-filter-v4_json
                leaf flowspec_community_route-filter-v4_json_detail {
                    type enumeration {
                        enum flowspec_community_route-filter-v4_json_detail;
                    }
                }                  //detail
                leaf flowspec_community_route-filter-translated-v6_exact-match {
                    type enumeration {
                        enum flowspec_community_route-filter-translated-v6_exact-match;
                    }
                }                  //flowspec_community_route-filter-translated-v6_exact-match
                leaf flowspec_community_route-filter-translated-v6_exact-match_wide {
                    type enumeration {
                        enum flowspec_community_route-filter-translated-v6_exact-match_wide;
                    }
                }                  //wide
                leaf flowspec_community_route-filter-translated-v6_json {
                    type enumeration {
                        enum flowspec_community_route-filter-translated-v6_json;
                    }
                }                  //flowspec_community_route-filter-translated-v6_json
                leaf flowspec_community_route-filter-translated-v6_json_detail {
                    type enumeration {
                        enum flowspec_community_route-filter-translated-v6_json_detail;
                    }
                }                  //detail
                leaf flowspec_community_route-filter-translated-v4_exact-match {
                    type enumeration {
                        enum flowspec_community_route-filter-translated-v4_exact-match;
                    }
                }                  //flowspec_community_route-filter-translated-v4_exact-match
                leaf flowspec_community_route-filter-translated-v4_exact-match_wide {
                    type enumeration {
                        enum flowspec_community_route-filter-translated-v4_exact-match_wide;
                    }
                }                  //wide
                leaf flowspec_community_route-filter-translated-v4_json {
                    type enumeration {
                        enum flowspec_community_route-filter-translated-v4_json;
                    }
                }                  //flowspec_community_route-filter-translated-v4_json
                leaf flowspec_community_route-filter-translated-v4_json_detail {
                    type enumeration {
                        enum flowspec_community_route-filter-translated-v4_json_detail;
                    }
                }                  //detail
                leaf flowspec_community_exact-match_json {
                    type enumeration {
                        enum flowspec_community_exact-match_json;
                    }
                }                  //flowspec_community_exact-match_json
                leaf flowspec_community_exact-match_json_detail {
                    type enumeration {
                        enum flowspec_community_exact-match_json_detail;
                    }
                }                  //detail
                leaf flowspec_summary_established_terse {
                    type enumeration {
                        enum flowspec_summary_established_terse;
                    }
                }                  //flowspec_summary_established_terse
                leaf flowspec_summary_established_terse_json {
                    type enumeration {
                        enum flowspec_summary_established_terse_json;
                    }
                }                  //json
                leaf flowspec_summary_established_wide {
                    type enumeration {
                        enum flowspec_summary_established_wide;
                    }
                }                  //flowspec_summary_established_wide
                leaf flowspec_summary_established_wide_json {
                    type enumeration {
                        enum flowspec_summary_established_wide_json;
                    }
                }                  //json
                leaf flowspec_summary_failed_terse {
                    type enumeration {
                        enum flowspec_summary_failed_terse;
                    }
                }                  //flowspec_summary_failed_terse
                leaf flowspec_summary_failed_terse_json {
                    type enumeration {
                        enum flowspec_summary_failed_terse_json;
                    }
                }                  //json
                leaf flowspec_summary_failed_wide {
                    type enumeration {
                        enum flowspec_summary_failed_wide;
                    }
                }                  //flowspec_summary_failed_wide
                leaf flowspec_summary_failed_wide_json {
                    type enumeration {
                        enum flowspec_summary_failed_wide_json;
                    }
                }                  //json
                leaf flowspec_summary_terse_wide {
                    type enumeration {
                        enum flowspec_summary_terse_wide;
                    }
                }                  //flowspec_summary_terse_wide
                leaf flowspec_summary_terse_wide_json {
                    type enumeration {
                        enum flowspec_summary_terse_wide_json;
                    }
                }                  //json
                leaf unicast_all_community_local-AS_exact-match {
                    type enumeration {
                        enum unicast_all_community_local-AS_exact-match;
                    }
                }                  //unicast_all_community_local-AS_exact-match
                leaf unicast_all_community_local-AS_exact-match_wide {
                    type enumeration {
                        enum unicast_all_community_local-AS_exact-match_wide;
                    }
                }                  //wide
                leaf unicast_all_community_local-AS_json {
                    type enumeration {
                        enum unicast_all_community_local-AS_json;
                    }
                }                  //unicast_all_community_local-AS_json
                leaf unicast_all_community_local-AS_json_detail {
                    type enumeration {
                        enum unicast_all_community_local-AS_json_detail;
                    }
                }                  //detail
                leaf unicast_all_community_no-advertise_exact-match {
                    type enumeration {
                        enum unicast_all_community_no-advertise_exact-match;
                    }
                }                  //unicast_all_community_no-advertise_exact-match
                leaf unicast_all_community_no-advertise_exact-match_wide {
                    type enumeration {
                        enum unicast_all_community_no-advertise_exact-match_wide;
                    }
                }                  //wide
                leaf unicast_all_community_no-advertise_json {
                    type enumeration {
                        enum unicast_all_community_no-advertise_json;
                    }
                }                  //unicast_all_community_no-advertise_json
                leaf unicast_all_community_no-advertise_json_detail {
                    type enumeration {
                        enum unicast_all_community_no-advertise_json_detail;
                    }
                }                  //detail
                leaf unicast_all_community_no-export_exact-match {
                    type enumeration {
                        enum unicast_all_community_no-export_exact-match;
                    }
                }                  //unicast_all_community_no-export_exact-match
                leaf unicast_all_community_no-export_exact-match_wide {
                    type enumeration {
                        enum unicast_all_community_no-export_exact-match_wide;
                    }
                }                  //wide
                leaf unicast_all_community_no-export_json {
                    type enumeration {
                        enum unicast_all_community_no-export_json;
                    }
                }                  //unicast_all_community_no-export_json
                leaf unicast_all_community_no-export_json_detail {
                    type enumeration {
                        enum unicast_all_community_no-export_json_detail;
                    }
                }                  //detail
                leaf unicast_all_community_graceful-shutdown_exact-match {
                    type enumeration {
                        enum unicast_all_community_graceful-shutdown_exact-match;
                    }
                }                  //unicast_all_community_graceful-shutdown_exact-match
                leaf unicast_all_community_graceful-shutdown_exact-match_wide {
                    type enumeration {
                        enum unicast_all_community_graceful-shutdown_exact-match_wide;
                    }
                }                  //wide
                leaf unicast_all_community_graceful-shutdown_json {
                    type enumeration {
                        enum unicast_all_community_graceful-shutdown_json;
                    }
                }                  //unicast_all_community_graceful-shutdown_json
                leaf unicast_all_community_graceful-shutdown_json_detail {
                    type enumeration {
                        enum unicast_all_community_graceful-shutdown_json_detail;
                    }
                }                  //detail
                leaf unicast_all_community_no-peer_exact-match {
                    type enumeration {
                        enum unicast_all_community_no-peer_exact-match;
                    }
                }                  //unicast_all_community_no-peer_exact-match
                leaf unicast_all_community_no-peer_exact-match_wide {
                    type enumeration {
                        enum unicast_all_community_no-peer_exact-match_wide;
                    }
                }                  //wide
                leaf unicast_all_community_no-peer_json {
                    type enumeration {
                        enum unicast_all_community_no-peer_json;
                    }
                }                  //unicast_all_community_no-peer_json
                leaf unicast_all_community_no-peer_json_detail {
                    type enumeration {
                        enum unicast_all_community_no-peer_json_detail;
                    }
                }                  //detail
                leaf unicast_all_community_blackhole_exact-match {
                    type enumeration {
                        enum unicast_all_community_blackhole_exact-match;
                    }
                }                  //unicast_all_community_blackhole_exact-match
                leaf unicast_all_community_blackhole_exact-match_wide {
                    type enumeration {
                        enum unicast_all_community_blackhole_exact-match_wide;
                    }
                }                  //wide
                leaf unicast_all_community_blackhole_json {
                    type enumeration {
                        enum unicast_all_community_blackhole_json;
                    }
                }                  //unicast_all_community_blackhole_json
                leaf unicast_all_community_blackhole_json_detail {
                    type enumeration {
                        enum unicast_all_community_blackhole_json_detail;
                    }
                }                  //detail
                leaf unicast_all_community_llgr-stale_exact-match {
                    type enumeration {
                        enum unicast_all_community_llgr-stale_exact-match;
                    }
                }                  //unicast_all_community_llgr-stale_exact-match
                leaf unicast_all_community_llgr-stale_exact-match_wide {
                    type enumeration {
                        enum unicast_all_community_llgr-stale_exact-match_wide;
                    }
                }                  //wide
                leaf unicast_all_community_llgr-stale_json {
                    type enumeration {
                        enum unicast_all_community_llgr-stale_json;
                    }
                }                  //unicast_all_community_llgr-stale_json
                leaf unicast_all_community_llgr-stale_json_detail {
                    type enumeration {
                        enum unicast_all_community_llgr-stale_json_detail;
                    }
                }                  //detail
                leaf unicast_all_community_no-llgr_exact-match {
                    type enumeration {
                        enum unicast_all_community_no-llgr_exact-match;
                    }
                }                  //unicast_all_community_no-llgr_exact-match
                leaf unicast_all_community_no-llgr_exact-match_wide {
                    type enumeration {
                        enum unicast_all_community_no-llgr_exact-match_wide;
                    }
                }                  //wide
                leaf unicast_all_community_no-llgr_json {
                    type enumeration {
                        enum unicast_all_community_no-llgr_json;
                    }
                }                  //unicast_all_community_no-llgr_json
                leaf unicast_all_community_no-llgr_json_detail {
                    type enumeration {
                        enum unicast_all_community_no-llgr_json_detail;
                    }
                }                  //detail
                leaf unicast_all_community_accept-own_exact-match {
                    type enumeration {
                        enum unicast_all_community_accept-own_exact-match;
                    }
                }                  //unicast_all_community_accept-own_exact-match
                leaf unicast_all_community_accept-own_exact-match_wide {
                    type enumeration {
                        enum unicast_all_community_accept-own_exact-match_wide;
                    }
                }                  //wide
                leaf unicast_all_community_accept-own_json {
                    type enumeration {
                        enum unicast_all_community_accept-own_json;
                    }
                }                  //unicast_all_community_accept-own_json
                leaf unicast_all_community_accept-own_json_detail {
                    type enumeration {
                        enum unicast_all_community_accept-own_json_detail;
                    }
                }                  //detail
                leaf unicast_all_community_accept-own-nexthop_exact-match {
                    type enumeration {
                        enum unicast_all_community_accept-own-nexthop_exact-match;
                    }
                }                  //unicast_all_community_accept-own-nexthop_exact-match
                leaf unicast_all_community_accept-own-nexthop_exact-match_wide {
                    type enumeration {
                        enum unicast_all_community_accept-own-nexthop_exact-match_wide;
                    }
                }                  //wide
                leaf unicast_all_community_accept-own-nexthop_json {
                    type enumeration {
                        enum unicast_all_community_accept-own-nexthop_json;
                    }
                }                  //unicast_all_community_accept-own-nexthop_json
                leaf unicast_all_community_accept-own-nexthop_json_detail {
                    type enumeration {
                        enum unicast_all_community_accept-own-nexthop_json_detail;
                    }
                }                  //detail
                leaf unicast_all_community_route-filter-v6_exact-match {
                    type enumeration {
                        enum unicast_all_community_route-filter-v6_exact-match;
                    }
                }                  //unicast_all_community_route-filter-v6_exact-match
                leaf unicast_all_community_route-filter-v6_exact-match_wide {
                    type enumeration {
                        enum unicast_all_community_route-filter-v6_exact-match_wide;
                    }
                }                  //wide
                leaf unicast_all_community_route-filter-v6_json {
                    type enumeration {
                        enum unicast_all_community_route-filter-v6_json;
                    }
                }                  //unicast_all_community_route-filter-v6_json
                leaf unicast_all_community_route-filter-v6_json_detail {
                    type enumeration {
                        enum unicast_all_community_route-filter-v6_json_detail;
                    }
                }                  //detail
                leaf unicast_all_community_route-filter-v4_exact-match {
                    type enumeration {
                        enum unicast_all_community_route-filter-v4_exact-match;
                    }
                }                  //unicast_all_community_route-filter-v4_exact-match
                leaf unicast_all_community_route-filter-v4_exact-match_wide {
                    type enumeration {
                        enum unicast_all_community_route-filter-v4_exact-match_wide;
                    }
                }                  //wide
                leaf unicast_all_community_route-filter-v4_json {
                    type enumeration {
                        enum unicast_all_community_route-filter-v4_json;
                    }
                }                  //unicast_all_community_route-filter-v4_json
                leaf unicast_all_community_route-filter-v4_json_detail {
                    type enumeration {
                        enum unicast_all_community_route-filter-v4_json_detail;
                    }
                }                  //detail
                leaf unicast_all_community_route-filter-translated-v6_exact-match {
                    type enumeration {
                        enum unicast_all_community_route-filter-translated-v6_exact-match;
                    }
                }                  //unicast_all_community_route-filter-translated-v6_exact-match
                leaf unicast_all_community_route-filter-translated-v6_exact-match_wide {
                    type enumeration {
                        enum unicast_all_community_route-filter-translated-v6_exact-match_wide;
                    }
                }                  //wide
                leaf unicast_all_community_route-filter-translated-v6_json {
                    type enumeration {
                        enum unicast_all_community_route-filter-translated-v6_json;
                    }
                }                  //unicast_all_community_route-filter-translated-v6_json
                leaf unicast_all_community_route-filter-translated-v6_json_detail {
                    type enumeration {
                        enum unicast_all_community_route-filter-translated-v6_json_detail;
                    }
                }                  //detail
                leaf unicast_all_community_route-filter-translated-v4_exact-match {
                    type enumeration {
                        enum unicast_all_community_route-filter-translated-v4_exact-match;
                    }
                }                  //unicast_all_community_route-filter-translated-v4_exact-match
                leaf unicast_all_community_route-filter-translated-v4_exact-match_wide {
                    type enumeration {
                        enum unicast_all_community_route-filter-translated-v4_exact-match_wide;
                    }
                }                  //wide
                leaf unicast_all_community_route-filter-translated-v4_json {
                    type enumeration {
                        enum unicast_all_community_route-filter-translated-v4_json;
                    }
                }                  //unicast_all_community_route-filter-translated-v4_json
                leaf unicast_all_community_route-filter-translated-v4_json_detail {
                    type enumeration {
                        enum unicast_all_community_route-filter-translated-v4_json_detail;
                    }
                }                  //detail
                leaf unicast_all_community_exact-match_json {
                    type enumeration {
                        enum unicast_all_community_exact-match_json;
                    }
                }                  //unicast_all_community_exact-match_json
                leaf unicast_all_community_exact-match_json_detail {
                    type enumeration {
                        enum unicast_all_community_exact-match_json_detail;
                    }
                }                  //detail
                leaf unicast_all_summary_established_terse {
                    type enumeration {
                        enum unicast_all_summary_established_terse;
                    }
                }                  //unicast_all_summary_established_terse
                leaf unicast_all_summary_established_terse_json {
                    type enumeration {
                        enum unicast_all_summary_established_terse_json;
                    }
                }                  //json
                leaf unicast_all_summary_established_wide {
                    type enumeration {
                        enum unicast_all_summary_established_wide;
                    }
                }                  //unicast_all_summary_established_wide
                leaf unicast_all_summary_established_wide_json {
                    type enumeration {
                        enum unicast_all_summary_established_wide_json;
                    }
                }                  //json
                leaf unicast_all_summary_failed_terse {
                    type enumeration {
                        enum unicast_all_summary_failed_terse;
                    }
                }                  //unicast_all_summary_failed_terse
                leaf unicast_all_summary_failed_terse_json {
                    type enumeration {
                        enum unicast_all_summary_failed_terse_json;
                    }
                }                  //json
                leaf unicast_all_summary_failed_wide {
                    type enumeration {
                        enum unicast_all_summary_failed_wide;
                    }
                }                  //unicast_all_summary_failed_wide
                leaf unicast_all_summary_failed_wide_json {
                    type enumeration {
                        enum unicast_all_summary_failed_wide_json;
                    }
                }                  //json
                leaf unicast_all_summary_terse_wide {
                    type enumeration {
                        enum unicast_all_summary_terse_wide;
                    }
                }                  //unicast_all_summary_terse_wide
                leaf unicast_all_summary_terse_wide_json {
                    type enumeration {
                        enum unicast_all_summary_terse_wide_json;
                    }
                }                  //json
                leaf unicast_community_local-AS_exact-match_json {
                    type enumeration {
                        enum unicast_community_local-AS_exact-match_json;
                    }
                }                  //unicast_community_local-AS_exact-match_json
                leaf unicast_community_local-AS_exact-match_json_detail {
                    type enumeration {
                        enum unicast_community_local-AS_exact-match_json_detail;
                    }
                }                  //detail
                leaf unicast_community_no-advertise_exact-match_json {
                    type enumeration {
                        enum unicast_community_no-advertise_exact-match_json;
                    }
                }                  //unicast_community_no-advertise_exact-match_json
                leaf unicast_community_no-advertise_exact-match_json_detail {
                    type enumeration {
                        enum unicast_community_no-advertise_exact-match_json_detail;
                    }
                }                  //detail
                leaf unicast_community_no-export_exact-match_json {
                    type enumeration {
                        enum unicast_community_no-export_exact-match_json;
                    }
                }                  //unicast_community_no-export_exact-match_json
                leaf unicast_community_no-export_exact-match_json_detail {
                    type enumeration {
                        enum unicast_community_no-export_exact-match_json_detail;
                    }
                }                  //detail
                leaf unicast_community_graceful-shutdown_exact-match_json {
                    type enumeration {
                        enum unicast_community_graceful-shutdown_exact-match_json;
                    }
                }                  //unicast_community_graceful-shutdown_exact-match_json
                leaf unicast_community_graceful-shutdown_exact-match_json_detail {
                    type enumeration {
                        enum unicast_community_graceful-shutdown_exact-match_json_detail;
                    }
                }                  //detail
                leaf unicast_community_no-peer_exact-match_json {
                    type enumeration {
                        enum unicast_community_no-peer_exact-match_json;
                    }
                }                  //unicast_community_no-peer_exact-match_json
                leaf unicast_community_no-peer_exact-match_json_detail {
                    type enumeration {
                        enum unicast_community_no-peer_exact-match_json_detail;
                    }
                }                  //detail
                leaf unicast_community_blackhole_exact-match_json {
                    type enumeration {
                        enum unicast_community_blackhole_exact-match_json;
                    }
                }                  //unicast_community_blackhole_exact-match_json
                leaf unicast_community_blackhole_exact-match_json_detail {
                    type enumeration {
                        enum unicast_community_blackhole_exact-match_json_detail;
                    }
                }                  //detail
                leaf unicast_community_llgr-stale_exact-match_json {
                    type enumeration {
                        enum unicast_community_llgr-stale_exact-match_json;
                    }
                }                  //unicast_community_llgr-stale_exact-match_json
                leaf unicast_community_llgr-stale_exact-match_json_detail {
                    type enumeration {
                        enum unicast_community_llgr-stale_exact-match_json_detail;
                    }
                }                  //detail
                leaf unicast_community_no-llgr_exact-match_json {
                    type enumeration {
                        enum unicast_community_no-llgr_exact-match_json;
                    }
                }                  //unicast_community_no-llgr_exact-match_json
                leaf unicast_community_no-llgr_exact-match_json_detail {
                    type enumeration {
                        enum unicast_community_no-llgr_exact-match_json_detail;
                    }
                }                  //detail
                leaf unicast_community_accept-own_exact-match_json {
                    type enumeration {
                        enum unicast_community_accept-own_exact-match_json;
                    }
                }                  //unicast_community_accept-own_exact-match_json
                leaf unicast_community_accept-own_exact-match_json_detail {
                    type enumeration {
                        enum unicast_community_accept-own_exact-match_json_detail;
                    }
                }                  //detail
                leaf unicast_community_accept-own-nexthop_exact-match_json {
                    type enumeration {
                        enum unicast_community_accept-own-nexthop_exact-match_json;
                    }
                }                  //unicast_community_accept-own-nexthop_exact-match_json
                leaf unicast_community_accept-own-nexthop_exact-match_json_detail {
                    type enumeration {
                        enum unicast_community_accept-own-nexthop_exact-match_json_detail;
                    }
                }                  //detail
                leaf unicast_community_route-filter-v6_exact-match_json {
                    type enumeration {
                        enum unicast_community_route-filter-v6_exact-match_json;
                    }
                }                  //unicast_community_route-filter-v6_exact-match_json
                leaf unicast_community_route-filter-v6_exact-match_json_detail {
                    type enumeration {
                        enum unicast_community_route-filter-v6_exact-match_json_detail;
                    }
                }                  //detail
                leaf unicast_community_route-filter-v4_exact-match_json {
                    type enumeration {
                        enum unicast_community_route-filter-v4_exact-match_json;
                    }
                }                  //unicast_community_route-filter-v4_exact-match_json
                leaf unicast_community_route-filter-v4_exact-match_json_detail {
                    type enumeration {
                        enum unicast_community_route-filter-v4_exact-match_json_detail;
                    }
                }                  //detail
                leaf unicast_community_route-filter-translated-v6_exact-match_json {
                    type enumeration {
                        enum unicast_community_route-filter-translated-v6_exact-match_json;
                    }
                }                  //unicast_community_route-filter-translated-v6_exact-match_json
                leaf unicast_community_route-filter-translated-v6_exact-match_json_detail {
                    type enumeration {
                        enum unicast_community_route-filter-translated-v6_exact-match_json_detail;
                    }
                }                  //detail
                leaf unicast_community_route-filter-translated-v4_exact-match_json {
                    type enumeration {
                        enum unicast_community_route-filter-translated-v4_exact-match_json;
                    }
                }                  //unicast_community_route-filter-translated-v4_exact-match_json
                leaf unicast_community_route-filter-translated-v4_exact-match_json_detail {
                    type enumeration {
                        enum unicast_community_route-filter-translated-v4_exact-match_json_detail;
                    }
                }                  //detail
                leaf unicast_summary_established_terse_wide {
                    type enumeration {
                        enum unicast_summary_established_terse_wide;
                    }
                }                  //unicast_summary_established_terse_wide
                leaf unicast_summary_established_terse_wide_json {
                    type enumeration {
                        enum unicast_summary_established_terse_wide_json;
                    }
                }                  //json
                leaf unicast_summary_failed_terse_wide {
                    type enumeration {
                        enum unicast_summary_failed_terse_wide;
                    }
                }                  //unicast_summary_failed_terse_wide
                leaf unicast_summary_failed_terse_wide_json {
                    type enumeration {
                        enum unicast_summary_failed_terse_wide_json;
                    }
                }                  //json
                leaf flowspec_all_community_local-AS_exact-match {
                    type enumeration {
                        enum flowspec_all_community_local-AS_exact-match;
                    }
                }                  //flowspec_all_community_local-AS_exact-match
                leaf flowspec_all_community_local-AS_exact-match_wide {
                    type enumeration {
                        enum flowspec_all_community_local-AS_exact-match_wide;
                    }
                }                  //wide
                leaf flowspec_all_community_local-AS_json {
                    type enumeration {
                        enum flowspec_all_community_local-AS_json;
                    }
                }                  //flowspec_all_community_local-AS_json
                leaf flowspec_all_community_local-AS_json_detail {
                    type enumeration {
                        enum flowspec_all_community_local-AS_json_detail;
                    }
                }                  //detail
                leaf flowspec_all_community_no-advertise_exact-match {
                    type enumeration {
                        enum flowspec_all_community_no-advertise_exact-match;
                    }
                }                  //flowspec_all_community_no-advertise_exact-match
                leaf flowspec_all_community_no-advertise_exact-match_wide {
                    type enumeration {
                        enum flowspec_all_community_no-advertise_exact-match_wide;
                    }
                }                  //wide
                leaf flowspec_all_community_no-advertise_json {
                    type enumeration {
                        enum flowspec_all_community_no-advertise_json;
                    }
                }                  //flowspec_all_community_no-advertise_json
                leaf flowspec_all_community_no-advertise_json_detail {
                    type enumeration {
                        enum flowspec_all_community_no-advertise_json_detail;
                    }
                }                  //detail
                leaf flowspec_all_community_no-export_exact-match {
                    type enumeration {
                        enum flowspec_all_community_no-export_exact-match;
                    }
                }                  //flowspec_all_community_no-export_exact-match
                leaf flowspec_all_community_no-export_exact-match_wide {
                    type enumeration {
                        enum flowspec_all_community_no-export_exact-match_wide;
                    }
                }                  //wide
                leaf flowspec_all_community_no-export_json {
                    type enumeration {
                        enum flowspec_all_community_no-export_json;
                    }
                }                  //flowspec_all_community_no-export_json
                leaf flowspec_all_community_no-export_json_detail {
                    type enumeration {
                        enum flowspec_all_community_no-export_json_detail;
                    }
                }                  //detail
                leaf flowspec_all_community_graceful-shutdown_exact-match {
                    type enumeration {
                        enum flowspec_all_community_graceful-shutdown_exact-match;
                    }
                }                  //flowspec_all_community_graceful-shutdown_exact-match
                leaf flowspec_all_community_graceful-shutdown_exact-match_wide {
                    type enumeration {
                        enum flowspec_all_community_graceful-shutdown_exact-match_wide;
                    }
                }                  //wide
                leaf flowspec_all_community_graceful-shutdown_json {
                    type enumeration {
                        enum flowspec_all_community_graceful-shutdown_json;
                    }
                }                  //flowspec_all_community_graceful-shutdown_json
                leaf flowspec_all_community_graceful-shutdown_json_detail {
                    type enumeration {
                        enum flowspec_all_community_graceful-shutdown_json_detail;
                    }
                }                  //detail
                leaf flowspec_all_community_no-peer_exact-match {
                    type enumeration {
                        enum flowspec_all_community_no-peer_exact-match;
                    }
                }                  //flowspec_all_community_no-peer_exact-match
                leaf flowspec_all_community_no-peer_exact-match_wide {
                    type enumeration {
                        enum flowspec_all_community_no-peer_exact-match_wide;
                    }
                }                  //wide
                leaf flowspec_all_community_no-peer_json {
                    type enumeration {
                        enum flowspec_all_community_no-peer_json;
                    }
                }                  //flowspec_all_community_no-peer_json
                leaf flowspec_all_community_no-peer_json_detail {
                    type enumeration {
                        enum flowspec_all_community_no-peer_json_detail;
                    }
                }                  //detail
                leaf flowspec_all_community_blackhole_exact-match {
                    type enumeration {
                        enum flowspec_all_community_blackhole_exact-match;
                    }
                }                  //flowspec_all_community_blackhole_exact-match
                leaf flowspec_all_community_blackhole_exact-match_wide {
                    type enumeration {
                        enum flowspec_all_community_blackhole_exact-match_wide;
                    }
                }                  //wide
                leaf flowspec_all_community_blackhole_json {
                    type enumeration {
                        enum flowspec_all_community_blackhole_json;
                    }
                }                  //flowspec_all_community_blackhole_json
                leaf flowspec_all_community_blackhole_json_detail {
                    type enumeration {
                        enum flowspec_all_community_blackhole_json_detail;
                    }
                }                  //detail
                leaf flowspec_all_community_llgr-stale_exact-match {
                    type enumeration {
                        enum flowspec_all_community_llgr-stale_exact-match;
                    }
                }                  //flowspec_all_community_llgr-stale_exact-match
                leaf flowspec_all_community_llgr-stale_exact-match_wide {
                    type enumeration {
                        enum flowspec_all_community_llgr-stale_exact-match_wide;
                    }
                }                  //wide
                leaf flowspec_all_community_llgr-stale_json {
                    type enumeration {
                        enum flowspec_all_community_llgr-stale_json;
                    }
                }                  //flowspec_all_community_llgr-stale_json
                leaf flowspec_all_community_llgr-stale_json_detail {
                    type enumeration {
                        enum flowspec_all_community_llgr-stale_json_detail;
                    }
                }                  //detail
                leaf flowspec_all_community_no-llgr_exact-match {
                    type enumeration {
                        enum flowspec_all_community_no-llgr_exact-match;
                    }
                }                  //flowspec_all_community_no-llgr_exact-match
                leaf flowspec_all_community_no-llgr_exact-match_wide {
                    type enumeration {
                        enum flowspec_all_community_no-llgr_exact-match_wide;
                    }
                }                  //wide
                leaf flowspec_all_community_no-llgr_json {
                    type enumeration {
                        enum flowspec_all_community_no-llgr_json;
                    }
                }                  //flowspec_all_community_no-llgr_json
                leaf flowspec_all_community_no-llgr_json_detail {
                    type enumeration {
                        enum flowspec_all_community_no-llgr_json_detail;
                    }
                }                  //detail
                leaf flowspec_all_community_accept-own_exact-match {
                    type enumeration {
                        enum flowspec_all_community_accept-own_exact-match;
                    }
                }                  //flowspec_all_community_accept-own_exact-match
                leaf flowspec_all_community_accept-own_exact-match_wide {
                    type enumeration {
                        enum flowspec_all_community_accept-own_exact-match_wide;
                    }
                }                  //wide
                leaf flowspec_all_community_accept-own_json {
                    type enumeration {
                        enum flowspec_all_community_accept-own_json;
                    }
                }                  //flowspec_all_community_accept-own_json
                leaf flowspec_all_community_accept-own_json_detail {
                    type enumeration {
                        enum flowspec_all_community_accept-own_json_detail;
                    }
                }                  //detail
                leaf flowspec_all_community_accept-own-nexthop_exact-match {
                    type enumeration {
                        enum flowspec_all_community_accept-own-nexthop_exact-match;
                    }
                }                  //flowspec_all_community_accept-own-nexthop_exact-match
                leaf flowspec_all_community_accept-own-nexthop_exact-match_wide {
                    type enumeration {
                        enum flowspec_all_community_accept-own-nexthop_exact-match_wide;
                    }
                }                  //wide
                leaf flowspec_all_community_accept-own-nexthop_json {
                    type enumeration {
                        enum flowspec_all_community_accept-own-nexthop_json;
                    }
                }                  //flowspec_all_community_accept-own-nexthop_json
                leaf flowspec_all_community_accept-own-nexthop_json_detail {
                    type enumeration {
                        enum flowspec_all_community_accept-own-nexthop_json_detail;
                    }
                }                  //detail
                leaf flowspec_all_community_route-filter-v6_exact-match {
                    type enumeration {
                        enum flowspec_all_community_route-filter-v6_exact-match;
                    }
                }                  //flowspec_all_community_route-filter-v6_exact-match
                leaf flowspec_all_community_route-filter-v6_exact-match_wide {
                    type enumeration {
                        enum flowspec_all_community_route-filter-v6_exact-match_wide;
                    }
                }                  //wide
                leaf flowspec_all_community_route-filter-v6_json {
                    type enumeration {
                        enum flowspec_all_community_route-filter-v6_json;
                    }
                }                  //flowspec_all_community_route-filter-v6_json
                leaf flowspec_all_community_route-filter-v6_json_detail {
                    type enumeration {
                        enum flowspec_all_community_route-filter-v6_json_detail;
                    }
                }                  //detail
                leaf flowspec_all_community_route-filter-v4_exact-match {
                    type enumeration {
                        enum flowspec_all_community_route-filter-v4_exact-match;
                    }
                }                  //flowspec_all_community_route-filter-v4_exact-match
                leaf flowspec_all_community_route-filter-v4_exact-match_wide {
                    type enumeration {
                        enum flowspec_all_community_route-filter-v4_exact-match_wide;
                    }
                }                  //wide
                leaf flowspec_all_community_route-filter-v4_json {
                    type enumeration {
                        enum flowspec_all_community_route-filter-v4_json;
                    }
                }                  //flowspec_all_community_route-filter-v4_json
                leaf flowspec_all_community_route-filter-v4_json_detail {
                    type enumeration {
                        enum flowspec_all_community_route-filter-v4_json_detail;
                    }
                }                  //detail
                leaf flowspec_all_community_route-filter-translated-v6_exact-match {
                    type enumeration {
                        enum flowspec_all_community_route-filter-translated-v6_exact-match;
                    }
                }                  //flowspec_all_community_route-filter-translated-v6_exact-match
                leaf flowspec_all_community_route-filter-translated-v6_exact-match_wide {
                    type enumeration {
                        enum flowspec_all_community_route-filter-translated-v6_exact-match_wide;
                    }
                }                  //wide
                leaf flowspec_all_community_route-filter-translated-v6_json {
                    type enumeration {
                        enum flowspec_all_community_route-filter-translated-v6_json;
                    }
                }                  //flowspec_all_community_route-filter-translated-v6_json
                leaf flowspec_all_community_route-filter-translated-v6_json_detail {
                    type enumeration {
                        enum flowspec_all_community_route-filter-translated-v6_json_detail;
                    }
                }                  //detail
                leaf flowspec_all_community_route-filter-translated-v4_exact-match {
                    type enumeration {
                        enum flowspec_all_community_route-filter-translated-v4_exact-match;
                    }
                }                  //flowspec_all_community_route-filter-translated-v4_exact-match
                leaf flowspec_all_community_route-filter-translated-v4_exact-match_wide {
                    type enumeration {
                        enum flowspec_all_community_route-filter-translated-v4_exact-match_wide;
                    }
                }                  //wide
                leaf flowspec_all_community_route-filter-translated-v4_json {
                    type enumeration {
                        enum flowspec_all_community_route-filter-translated-v4_json;
                    }
                }                  //flowspec_all_community_route-filter-translated-v4_json
                leaf flowspec_all_community_route-filter-translated-v4_json_detail {
                    type enumeration {
                        enum flowspec_all_community_route-filter-translated-v4_json_detail;
                    }
                }                  //detail
                leaf flowspec_all_community_exact-match_json {
                    type enumeration {
                        enum flowspec_all_community_exact-match_json;
                    }
                }                  //flowspec_all_community_exact-match_json
                leaf flowspec_all_community_exact-match_json_detail {
                    type enumeration {
                        enum flowspec_all_community_exact-match_json_detail;
                    }
                }                  //detail
                leaf flowspec_all_summary_established_terse {
                    type enumeration {
                        enum flowspec_all_summary_established_terse;
                    }
                }                  //flowspec_all_summary_established_terse
                leaf flowspec_all_summary_established_terse_json {
                    type enumeration {
                        enum flowspec_all_summary_established_terse_json;
                    }
                }                  //json
                leaf flowspec_all_summary_established_wide {
                    type enumeration {
                        enum flowspec_all_summary_established_wide;
                    }
                }                  //flowspec_all_summary_established_wide
                leaf flowspec_all_summary_established_wide_json {
                    type enumeration {
                        enum flowspec_all_summary_established_wide_json;
                    }
                }                  //json
                leaf flowspec_all_summary_failed_terse {
                    type enumeration {
                        enum flowspec_all_summary_failed_terse;
                    }
                }                  //flowspec_all_summary_failed_terse
                leaf flowspec_all_summary_failed_terse_json {
                    type enumeration {
                        enum flowspec_all_summary_failed_terse_json;
                    }
                }                  //json
                leaf flowspec_all_summary_failed_wide {
                    type enumeration {
                        enum flowspec_all_summary_failed_wide;
                    }
                }                  //flowspec_all_summary_failed_wide
                leaf flowspec_all_summary_failed_wide_json {
                    type enumeration {
                        enum flowspec_all_summary_failed_wide_json;
                    }
                }                  //json
                leaf flowspec_all_summary_terse_wide {
                    type enumeration {
                        enum flowspec_all_summary_terse_wide;
                    }
                }                  //flowspec_all_summary_terse_wide
                leaf flowspec_all_summary_terse_wide_json {
                    type enumeration {
                        enum flowspec_all_summary_terse_wide_json;
                    }
                }                  //json
                leaf flowspec_community_local-AS_exact-match_json {
                    type enumeration {
                        enum flowspec_community_local-AS_exact-match_json;
                    }
                }                  //flowspec_community_local-AS_exact-match_json
                leaf flowspec_community_local-AS_exact-match_json_detail {
                    type enumeration {
                        enum flowspec_community_local-AS_exact-match_json_detail;
                    }
                }                  //detail
                leaf flowspec_community_no-advertise_exact-match_json {
                    type enumeration {
                        enum flowspec_community_no-advertise_exact-match_json;
                    }
                }                  //flowspec_community_no-advertise_exact-match_json
                leaf flowspec_community_no-advertise_exact-match_json_detail {
                    type enumeration {
                        enum flowspec_community_no-advertise_exact-match_json_detail;
                    }
                }                  //detail
                leaf flowspec_community_no-export_exact-match_json {
                    type enumeration {
                        enum flowspec_community_no-export_exact-match_json;
                    }
                }                  //flowspec_community_no-export_exact-match_json
                leaf flowspec_community_no-export_exact-match_json_detail {
                    type enumeration {
                        enum flowspec_community_no-export_exact-match_json_detail;
                    }
                }                  //detail
                leaf flowspec_community_graceful-shutdown_exact-match_json {
                    type enumeration {
                        enum flowspec_community_graceful-shutdown_exact-match_json;
                    }
                }                  //flowspec_community_graceful-shutdown_exact-match_json
                leaf flowspec_community_graceful-shutdown_exact-match_json_detail {
                    type enumeration {
                        enum flowspec_community_graceful-shutdown_exact-match_json_detail;
                    }
                }                  //detail
                leaf flowspec_community_no-peer_exact-match_json {
                    type enumeration {
                        enum flowspec_community_no-peer_exact-match_json;
                    }
                }                  //flowspec_community_no-peer_exact-match_json
                leaf flowspec_community_no-peer_exact-match_json_detail {
                    type enumeration {
                        enum flowspec_community_no-peer_exact-match_json_detail;
                    }
                }                  //detail
                leaf flowspec_community_blackhole_exact-match_json {
                    type enumeration {
                        enum flowspec_community_blackhole_exact-match_json;
                    }
                }                  //flowspec_community_blackhole_exact-match_json
                leaf flowspec_community_blackhole_exact-match_json_detail {
                    type enumeration {
                        enum flowspec_community_blackhole_exact-match_json_detail;
                    }
                }                  //detail
                leaf flowspec_community_llgr-stale_exact-match_json {
                    type enumeration {
                        enum flowspec_community_llgr-stale_exact-match_json;
                    }
                }                  //flowspec_community_llgr-stale_exact-match_json
                leaf flowspec_community_llgr-stale_exact-match_json_detail {
                    type enumeration {
                        enum flowspec_community_llgr-stale_exact-match_json_detail;
                    }
                }                  //detail
                leaf flowspec_community_no-llgr_exact-match_json {
                    type enumeration {
                        enum flowspec_community_no-llgr_exact-match_json;
                    }
                }                  //flowspec_community_no-llgr_exact-match_json
                leaf flowspec_community_no-llgr_exact-match_json_detail {
                    type enumeration {
                        enum flowspec_community_no-llgr_exact-match_json_detail;
                    }
                }                  //detail
                leaf flowspec_community_accept-own_exact-match_json {
                    type enumeration {
                        enum flowspec_community_accept-own_exact-match_json;
                    }
                }                  //flowspec_community_accept-own_exact-match_json
                leaf flowspec_community_accept-own_exact-match_json_detail {
                    type enumeration {
                        enum flowspec_community_accept-own_exact-match_json_detail;
                    }
                }                  //detail
                leaf flowspec_community_accept-own-nexthop_exact-match_json {
                    type enumeration {
                        enum flowspec_community_accept-own-nexthop_exact-match_json;
                    }
                }                  //flowspec_community_accept-own-nexthop_exact-match_json
                leaf flowspec_community_accept-own-nexthop_exact-match_json_detail {
                    type enumeration {
                        enum flowspec_community_accept-own-nexthop_exact-match_json_detail;
                    }
                }                  //detail
                leaf flowspec_community_route-filter-v6_exact-match_json {
                    type enumeration {
                        enum flowspec_community_route-filter-v6_exact-match_json;
                    }
                }                  //flowspec_community_route-filter-v6_exact-match_json
                leaf flowspec_community_route-filter-v6_exact-match_json_detail {
                    type enumeration {
                        enum flowspec_community_route-filter-v6_exact-match_json_detail;
                    }
                }                  //detail
                leaf flowspec_community_route-filter-v4_exact-match_json {
                    type enumeration {
                        enum flowspec_community_route-filter-v4_exact-match_json;
                    }
                }                  //flowspec_community_route-filter-v4_exact-match_json
                leaf flowspec_community_route-filter-v4_exact-match_json_detail {
                    type enumeration {
                        enum flowspec_community_route-filter-v4_exact-match_json_detail;
                    }
                }                  //detail
                leaf flowspec_community_route-filter-translated-v6_exact-match_json {
                    type enumeration {
                        enum flowspec_community_route-filter-translated-v6_exact-match_json;
                    }
                }                  //flowspec_community_route-filter-translated-v6_exact-match_json
                leaf flowspec_community_route-filter-translated-v6_exact-match_json_detail {
                    type enumeration {
                        enum flowspec_community_route-filter-translated-v6_exact-match_json_detail;
                    }
                }                  //detail
                leaf flowspec_community_route-filter-translated-v4_exact-match_json {
                    type enumeration {
                        enum flowspec_community_route-filter-translated-v4_exact-match_json;
                    }
                }                  //flowspec_community_route-filter-translated-v4_exact-match_json
                leaf flowspec_community_route-filter-translated-v4_exact-match_json_detail {
                    type enumeration {
                        enum flowspec_community_route-filter-translated-v4_exact-match_json_detail;
                    }
                }                  //detail
                leaf flowspec_summary_established_terse_wide {
                    type enumeration {
                        enum flowspec_summary_established_terse_wide;
                    }
                }                  //flowspec_summary_established_terse_wide
                leaf flowspec_summary_established_terse_wide_json {
                    type enumeration {
                        enum flowspec_summary_established_terse_wide_json;
                    }
                }                  //json
                leaf flowspec_summary_failed_terse_wide {
                    type enumeration {
                        enum flowspec_summary_failed_terse_wide;
                    }
                }                  //flowspec_summary_failed_terse_wide
                leaf flowspec_summary_failed_terse_wide_json {
                    type enumeration {
                        enum flowspec_summary_failed_terse_wide_json;
                    }
                }                  //json
                leaf unicast_all_community_local-AS_exact-match_json {
                    type enumeration {
                        enum unicast_all_community_local-AS_exact-match_json;
                    }
                }                  //unicast_all_community_local-AS_exact-match_json
                leaf unicast_all_community_local-AS_exact-match_json_detail {
                    type enumeration {
                        enum unicast_all_community_local-AS_exact-match_json_detail;
                    }
                }                  //detail
                leaf unicast_all_community_no-advertise_exact-match_json {
                    type enumeration {
                        enum unicast_all_community_no-advertise_exact-match_json;
                    }
                }                  //unicast_all_community_no-advertise_exact-match_json
                leaf unicast_all_community_no-advertise_exact-match_json_detail {
                    type enumeration {
                        enum unicast_all_community_no-advertise_exact-match_json_detail;
                    }
                }                  //detail
                leaf unicast_all_community_no-export_exact-match_json {
                    type enumeration {
                        enum unicast_all_community_no-export_exact-match_json;
                    }
                }                  //unicast_all_community_no-export_exact-match_json
                leaf unicast_all_community_no-export_exact-match_json_detail {
                    type enumeration {
                        enum unicast_all_community_no-export_exact-match_json_detail;
                    }
                }                  //detail
                leaf unicast_all_community_graceful-shutdown_exact-match_json {
                    type enumeration {
                        enum unicast_all_community_graceful-shutdown_exact-match_json;
                    }
                }                  //unicast_all_community_graceful-shutdown_exact-match_json
                leaf unicast_all_community_graceful-shutdown_exact-match_json_detail {
                    type enumeration {
                        enum unicast_all_community_graceful-shutdown_exact-match_json_detail;
                    }
                }                  //detail
                leaf unicast_all_community_no-peer_exact-match_json {
                    type enumeration {
                        enum unicast_all_community_no-peer_exact-match_json;
                    }
                }                  //unicast_all_community_no-peer_exact-match_json
                leaf unicast_all_community_no-peer_exact-match_json_detail {
                    type enumeration {
                        enum unicast_all_community_no-peer_exact-match_json_detail;
                    }
                }                  //detail
                leaf unicast_all_community_blackhole_exact-match_json {
                    type enumeration {
                        enum unicast_all_community_blackhole_exact-match_json;
                    }
                }                  //unicast_all_community_blackhole_exact-match_json
                leaf unicast_all_community_blackhole_exact-match_json_detail {
                    type enumeration {
                        enum unicast_all_community_blackhole_exact-match_json_detail;
                    }
                }                  //detail
                leaf unicast_all_community_llgr-stale_exact-match_json {
                    type enumeration {
                        enum unicast_all_community_llgr-stale_exact-match_json;
                    }
                }                  //unicast_all_community_llgr-stale_exact-match_json
                leaf unicast_all_community_llgr-stale_exact-match_json_detail {
                    type enumeration {
                        enum unicast_all_community_llgr-stale_exact-match_json_detail;
                    }
                }                  //detail
                leaf unicast_all_community_no-llgr_exact-match_json {
                    type enumeration {
                        enum unicast_all_community_no-llgr_exact-match_json;
                    }
                }                  //unicast_all_community_no-llgr_exact-match_json
                leaf unicast_all_community_no-llgr_exact-match_json_detail {
                    type enumeration {
                        enum unicast_all_community_no-llgr_exact-match_json_detail;
                    }
                }                  //detail
                leaf unicast_all_community_accept-own_exact-match_json {
                    type enumeration {
                        enum unicast_all_community_accept-own_exact-match_json;
                    }
                }                  //unicast_all_community_accept-own_exact-match_json
                leaf unicast_all_community_accept-own_exact-match_json_detail {
                    type enumeration {
                        enum unicast_all_community_accept-own_exact-match_json_detail;
                    }
                }                  //detail
                leaf unicast_all_community_accept-own-nexthop_exact-match_json {
                    type enumeration {
                        enum unicast_all_community_accept-own-nexthop_exact-match_json;
                    }
                }                  //unicast_all_community_accept-own-nexthop_exact-match_json
                leaf unicast_all_community_accept-own-nexthop_exact-match_json_detail {
                    type enumeration {
                        enum unicast_all_community_accept-own-nexthop_exact-match_json_detail;
                    }
                }                  //detail
                leaf unicast_all_community_route-filter-v6_exact-match_json {
                    type enumeration {
                        enum unicast_all_community_route-filter-v6_exact-match_json;
                    }
                }                  //unicast_all_community_route-filter-v6_exact-match_json
                leaf unicast_all_community_route-filter-v6_exact-match_json_detail {
                    type enumeration {
                        enum unicast_all_community_route-filter-v6_exact-match_json_detail;
                    }
                }                  //detail
                leaf unicast_all_community_route-filter-v4_exact-match_json {
                    type enumeration {
                        enum unicast_all_community_route-filter-v4_exact-match_json;
                    }
                }                  //unicast_all_community_route-filter-v4_exact-match_json
                leaf unicast_all_community_route-filter-v4_exact-match_json_detail {
                    type enumeration {
                        enum unicast_all_community_route-filter-v4_exact-match_json_detail;
                    }
                }                  //detail
                leaf unicast_all_community_route-filter-translated-v6_exact-match_json {
                    type enumeration {
                        enum unicast_all_community_route-filter-translated-v6_exact-match_json;
                    }
                }                  //unicast_all_community_route-filter-translated-v6_exact-match_json
                leaf unicast_all_community_route-filter-translated-v6_exact-match_json_detail {
                    type enumeration {
                        enum unicast_all_community_route-filter-translated-v6_exact-match_json_detail;
                    }
                }                  //detail
                leaf unicast_all_community_route-filter-translated-v4_exact-match_json {
                    type enumeration {
                        enum unicast_all_community_route-filter-translated-v4_exact-match_json;
                    }
                }                  //unicast_all_community_route-filter-translated-v4_exact-match_json
                leaf unicast_all_community_route-filter-translated-v4_exact-match_json_detail {
                    type enumeration {
                        enum unicast_all_community_route-filter-translated-v4_exact-match_json_detail;
                    }
                }                  //detail
                leaf unicast_all_summary_established_terse_wide {
                    type enumeration {
                        enum unicast_all_summary_established_terse_wide;
                    }
                }                  //unicast_all_summary_established_terse_wide
                leaf unicast_all_summary_established_terse_wide_json {
                    type enumeration {
                        enum unicast_all_summary_established_terse_wide_json;
                    }
                }                  //json
                leaf unicast_all_summary_failed_terse_wide {
                    type enumeration {
                        enum unicast_all_summary_failed_terse_wide;
                    }
                }                  //unicast_all_summary_failed_terse_wide
                leaf unicast_all_summary_failed_terse_wide_json {
                    type enumeration {
                        enum unicast_all_summary_failed_terse_wide_json;
                    }
                }                  //json
                leaf flowspec_all_community_local-AS_exact-match_json {
                    type enumeration {
                        enum flowspec_all_community_local-AS_exact-match_json;
                    }
                }                  //flowspec_all_community_local-AS_exact-match_json
                leaf flowspec_all_community_local-AS_exact-match_json_detail {
                    type enumeration {
                        enum flowspec_all_community_local-AS_exact-match_json_detail;
                    }
                }                  //detail
                leaf flowspec_all_community_no-advertise_exact-match_json {
                    type enumeration {
                        enum flowspec_all_community_no-advertise_exact-match_json;
                    }
                }                  //flowspec_all_community_no-advertise_exact-match_json
                leaf flowspec_all_community_no-advertise_exact-match_json_detail {
                    type enumeration {
                        enum flowspec_all_community_no-advertise_exact-match_json_detail;
                    }
                }                  //detail
                leaf flowspec_all_community_no-export_exact-match_json {
                    type enumeration {
                        enum flowspec_all_community_no-export_exact-match_json;
                    }
                }                  //flowspec_all_community_no-export_exact-match_json
                leaf flowspec_all_community_no-export_exact-match_json_detail {
                    type enumeration {
                        enum flowspec_all_community_no-export_exact-match_json_detail;
                    }
                }                  //detail
                leaf flowspec_all_community_graceful-shutdown_exact-match_json {
                    type enumeration {
                        enum flowspec_all_community_graceful-shutdown_exact-match_json;
                    }
                }                  //flowspec_all_community_graceful-shutdown_exact-match_json
                leaf flowspec_all_community_graceful-shutdown_exact-match_json_detail {
                    type enumeration {
                        enum flowspec_all_community_graceful-shutdown_exact-match_json_detail;
                    }
                }                  //detail
                leaf flowspec_all_community_no-peer_exact-match_json {
                    type enumeration {
                        enum flowspec_all_community_no-peer_exact-match_json;
                    }
                }                  //flowspec_all_community_no-peer_exact-match_json
                leaf flowspec_all_community_no-peer_exact-match_json_detail {
                    type enumeration {
                        enum flowspec_all_community_no-peer_exact-match_json_detail;
                    }
                }                  //detail
                leaf flowspec_all_community_blackhole_exact-match_json {
                    type enumeration {
                        enum flowspec_all_community_blackhole_exact-match_json;
                    }
                }                  //flowspec_all_community_blackhole_exact-match_json
                leaf flowspec_all_community_blackhole_exact-match_json_detail {
                    type enumeration {
                        enum flowspec_all_community_blackhole_exact-match_json_detail;
                    }
                }                  //detail
                leaf flowspec_all_community_llgr-stale_exact-match_json {
                    type enumeration {
                        enum flowspec_all_community_llgr-stale_exact-match_json;
                    }
                }                  //flowspec_all_community_llgr-stale_exact-match_json
                leaf flowspec_all_community_llgr-stale_exact-match_json_detail {
                    type enumeration {
                        enum flowspec_all_community_llgr-stale_exact-match_json_detail;
                    }
                }                  //detail
                leaf flowspec_all_community_no-llgr_exact-match_json {
                    type enumeration {
                        enum flowspec_all_community_no-llgr_exact-match_json;
                    }
                }                  //flowspec_all_community_no-llgr_exact-match_json
                leaf flowspec_all_community_no-llgr_exact-match_json_detail {
                    type enumeration {
                        enum flowspec_all_community_no-llgr_exact-match_json_detail;
                    }
                }                  //detail
                leaf flowspec_all_community_accept-own_exact-match_json {
                    type enumeration {
                        enum flowspec_all_community_accept-own_exact-match_json;
                    }
                }                  //flowspec_all_community_accept-own_exact-match_json
                leaf flowspec_all_community_accept-own_exact-match_json_detail {
                    type enumeration {
                        enum flowspec_all_community_accept-own_exact-match_json_detail;
                    }
                }                  //detail
                leaf flowspec_all_community_accept-own-nexthop_exact-match_json {
                    type enumeration {
                        enum flowspec_all_community_accept-own-nexthop_exact-match_json;
                    }
                }                  //flowspec_all_community_accept-own-nexthop_exact-match_json
                leaf flowspec_all_community_accept-own-nexthop_exact-match_json_detail {
                    type enumeration {
                        enum flowspec_all_community_accept-own-nexthop_exact-match_json_detail;
                    }
                }                  //detail
                leaf flowspec_all_community_route-filter-v6_exact-match_json {
                    type enumeration {
                        enum flowspec_all_community_route-filter-v6_exact-match_json;
                    }
                }                  //flowspec_all_community_route-filter-v6_exact-match_json
                leaf flowspec_all_community_route-filter-v6_exact-match_json_detail {
                    type enumeration {
                        enum flowspec_all_community_route-filter-v6_exact-match_json_detail;
                    }
                }                  //detail
                leaf flowspec_all_community_route-filter-v4_exact-match_json {
                    type enumeration {
                        enum flowspec_all_community_route-filter-v4_exact-match_json;
                    }
                }                  //flowspec_all_community_route-filter-v4_exact-match_json
                leaf flowspec_all_community_route-filter-v4_exact-match_json_detail {
                    type enumeration {
                        enum flowspec_all_community_route-filter-v4_exact-match_json_detail;
                    }
                }                  //detail
                leaf flowspec_all_community_route-filter-translated-v6_exact-match_json {
                    type enumeration {
                        enum flowspec_all_community_route-filter-translated-v6_exact-match_json;
                    }
                }                  //flowspec_all_community_route-filter-translated-v6_exact-match_json
                leaf flowspec_all_community_route-filter-translated-v6_exact-match_json_detail {
                    type enumeration {
                        enum flowspec_all_community_route-filter-translated-v6_exact-match_json_detail;
                    }
                }                  //detail
                leaf flowspec_all_community_route-filter-translated-v4_exact-match_json {
                    type enumeration {
                        enum flowspec_all_community_route-filter-translated-v4_exact-match_json;
                    }
                }                  //flowspec_all_community_route-filter-translated-v4_exact-match_json
                leaf flowspec_all_community_route-filter-translated-v4_exact-match_json_detail {
                    type enumeration {
                        enum flowspec_all_community_route-filter-translated-v4_exact-match_json_detail;
                    }
                }                  //detail
                leaf flowspec_all_summary_established_terse_wide {
                    type enumeration {
                        enum flowspec_all_summary_established_terse_wide;
                    }
                }                  //flowspec_all_summary_established_terse_wide
                leaf flowspec_all_summary_established_terse_wide_json {
                    type enumeration {
                        enum flowspec_all_summary_established_terse_wide_json;
                    }
                }                  //json
                leaf flowspec_all_summary_failed_terse_wide {
                    type enumeration {
                        enum flowspec_all_summary_failed_terse_wide;
                    }
                }                  //flowspec_all_summary_failed_terse_wide
                leaf flowspec_all_summary_failed_terse_wide_json {
                    type enumeration {
                        enum flowspec_all_summary_failed_terse_wide_json;
                    }
                }                  //json
                leaf peer-group {
                    type enumeration {
                        enum peer-group;
                    }
                }                  //peer-group
                leaf peer-group_json {
                    type enumeration {
                        enum peer-group_json;
                    }
                }                  //json
                leaf statistics-all {
                    type enumeration {
                        enum statistics-all;
                    }
                }                  //statistics-all
                leaf statistics-all_json {
                    type enumeration {
                        enum statistics-all_json;
                    }
                }                  //json
                leaf martian_next-hop {
                    type enumeration {
                        enum martian_next-hop;
                    }
                }                  //next-hop
                leaf l2vpn_evpn_statistics {
                    type enumeration {
                        enum l2vpn_evpn_statistics;
                    }
                }                  //l2vpn_evpn_statistics
                leaf l2vpn_evpn_statistics_json {
                    type enumeration {
                        enum l2vpn_evpn_statistics_json;
                    }
                }                  //json
                leaf VRF_NAME {
                    type string;
                }                  //VRFNAME
                leaf vni {
                    type enumeration {
                        enum vni;
                    }
                }                  //vni
                leaf vni_json {
                    type enumeration {
                        enum vni_json;
                    }
                }                  //json
                leaf l2vpn_evpn_summary {
                    type enumeration {
                        enum l2vpn_evpn_summary;
                    }
                }                  //l2vpn_evpn_summary
                leaf l2vpn_evpn_summary_neighbor {
                    type enumeration {
                        enum l2vpn_evpn_summary_neighbor;
                    }
                }                  //neighbor
                leaf l2vpn_evpn_summary_remote-as {
                    type enumeration {
                        enum l2vpn_evpn_summary_remote-as;
                    }
                }                  //remote-as
                leaf l2vpn_evpn_summary_json {
                    type enumeration {
                        enum l2vpn_evpn_summary_json;
                    }
                }                  //json
                leaf l2vpn_evpn_summary_established {
                    type enumeration {
                        enum l2vpn_evpn_summary_established;
                    }
                }                  //l2vpn_evpn_summary_established
                leaf l2vpn_evpn_summary_established_neighbor {
                    type enumeration {
                        enum l2vpn_evpn_summary_established_neighbor;
                    }
                }                  //neighbor
                leaf l2vpn_evpn_summary_established_remote-as {
                    type enumeration {
                        enum l2vpn_evpn_summary_established_remote-as;
                    }
                }                  //remote-as
                leaf l2vpn_evpn_summary_established_json {
                    type enumeration {
                        enum l2vpn_evpn_summary_established_json;
                    }
                }                  //json
                leaf l2vpn_evpn_summary_failed {
                    type enumeration {
                        enum l2vpn_evpn_summary_failed;
                    }
                }                  //l2vpn_evpn_summary_failed
                leaf l2vpn_evpn_summary_failed_neighbor {
                    type enumeration {
                        enum l2vpn_evpn_summary_failed_neighbor;
                    }
                }                  //neighbor
                leaf l2vpn_evpn_summary_failed_remote-as {
                    type enumeration {
                        enum l2vpn_evpn_summary_failed_remote-as;
                    }
                }                  //remote-as
                leaf l2vpn_evpn_summary_failed_json {
                    type enumeration {
                        enum l2vpn_evpn_summary_failed_json;
                    }
                }                  //json
                leaf l2vpn_evpn_summary_terse {
                    type enumeration {
                        enum l2vpn_evpn_summary_terse;
                    }
                }                  //l2vpn_evpn_summary_terse
                leaf l2vpn_evpn_summary_terse_json {
                    type enumeration {
                        enum l2vpn_evpn_summary_terse_json;
                    }
                }                  //json
                leaf l2vpn_evpn_summary_wide {
                    type enumeration {
                        enum l2vpn_evpn_summary_wide;
                    }
                }                  //l2vpn_evpn_summary_wide
                leaf l2vpn_evpn_summary_wide_json {
                    type enumeration {
                        enum l2vpn_evpn_summary_wide_json;
                    }
                }                  //json
                leaf l2vpn_evpn_summary_established_terse {
                    type enumeration {
                        enum l2vpn_evpn_summary_established_terse;
                    }
                }                  //l2vpn_evpn_summary_established_terse
                leaf l2vpn_evpn_summary_established_terse_json {
                    type enumeration {
                        enum l2vpn_evpn_summary_established_terse_json;
                    }
                }                  //json
                leaf l2vpn_evpn_summary_established_wide {
                    type enumeration {
                        enum l2vpn_evpn_summary_established_wide;
                    }
                }                  //l2vpn_evpn_summary_established_wide
                leaf l2vpn_evpn_summary_established_wide_json {
                    type enumeration {
                        enum l2vpn_evpn_summary_established_wide_json;
                    }
                }                  //json
                leaf l2vpn_evpn_summary_failed_terse {
                    type enumeration {
                        enum l2vpn_evpn_summary_failed_terse;
                    }
                }                  //l2vpn_evpn_summary_failed_terse
                leaf l2vpn_evpn_summary_failed_terse_json {
                    type enumeration {
                        enum l2vpn_evpn_summary_failed_terse_json;
                    }
                }                  //json
                leaf l2vpn_evpn_summary_failed_wide {
                    type enumeration {
                        enum l2vpn_evpn_summary_failed_wide;
                    }
                }                  //l2vpn_evpn_summary_failed_wide
                leaf l2vpn_evpn_summary_failed_wide_json {
                    type enumeration {
                        enum l2vpn_evpn_summary_failed_wide_json;
                    }
                }                  //json
                leaf l2vpn_evpn_summary_terse_wide {
                    type enumeration {
                        enum l2vpn_evpn_summary_terse_wide;
                    }
                }                  //l2vpn_evpn_summary_terse_wide
                leaf l2vpn_evpn_summary_terse_wide_json {
                    type enumeration {
                        enum l2vpn_evpn_summary_terse_wide_json;
                    }
                }                  //json
                leaf l2vpn_evpn_summary_established_terse_wide {
                    type enumeration {
                        enum l2vpn_evpn_summary_established_terse_wide;
                    }
                }                  //l2vpn_evpn_summary_established_terse_wide
                leaf l2vpn_evpn_summary_established_terse_wide_json {
                    type enumeration {
                        enum l2vpn_evpn_summary_established_terse_wide_json;
                    }
                }                  //json
                leaf l2vpn_evpn_summary_failed_terse_wide {
                    type enumeration {
                        enum l2vpn_evpn_summary_failed_terse_wide;
                    }
                }                  //l2vpn_evpn_summary_failed_terse_wide
                leaf l2vpn_evpn_summary_failed_terse_wide_json {
                    type enumeration {
                        enum l2vpn_evpn_summary_failed_terse_wide_json;
                    }
                }                  //json
            }
            container show_bgp_view {
                leaf VIEWVRF_NAME {
                    type string;
                }                  //VIEWVRFNAME
                leaf update-groups {
                    type enumeration {
                        enum update-groups;
                    }
                }                  //update-groups
                leaf update-groups_statistics {
                    type enumeration {
                        enum update-groups_statistics;
                    }
                }                  //statistics
                leaf ROUTING_QUEUE {
                    type enumeration {
                        enum advertise-queue;
                        enum advertised-routes;
                        enum packet-queue;
                    }
                }                  //<advertise-queue|advertised-routes|packet-queue> ['Advertisement queue', 'Announced routes', 'Packet queue']
                leaf update-groups_json {
                    type enumeration {
                        enum update-groups_json;
                    }
                }                  //json
                leaf REDISTRIBUTE_IP {
                    type enumeration {
                        enum ipv4;
                        enum ipv6;
                    }
                }                  //<ipv4|ipv6> ['Address Family', 'Address Family']
                leaf route-leak {
                    type enumeration {
                        enum route-leak;
                    }
                }                  //route-leak
                leaf route-leak_json {
                    type enumeration {
                        enum route-leak_json;
                    }
                }                  //json
                leaf all {
                    type enumeration {
                        enum all;
                    }
                }                  //all
                leaf all_community-list {
                    type enumeration {
                        enum all_community-list;
                    }
                }                  //community-list
                leaf COMMUNITY-LIST_NAME {
                    type union {
                        type int32;
                        type string;
                    }
                }                  //<(1-500)|COMMUNITY_LIST_NAME>
                leaf exact-match {
                    type enumeration {
                        enum exact-match;
                    }
                }                  //exact-match
                leaf exact-match_wide {
                    type enumeration {
                        enum exact-match_wide;
                    }
                }                  //wide
                leaf json {
                    type enumeration {
                        enum json;
                    }
                }                  //json
                leaf json_detail {
                    type enumeration {
                        enum json_detail;
                    }
                }                  //detail
                leaf wide {
                    type enumeration {
                        enum wide;
                    }
                }                  //wide
                leaf exact-match_json {
                    type enumeration {
                        enum exact-match_json;
                    }
                }                  //exact-match_json
                leaf exact-match_json_detail {
                    type enumeration {
                        enum exact-match_json_detail;
                    }
                }                  //detail
                leaf all_filter-list {
                    type enumeration {
                        enum all_filter-list;
                    }
                }                  //filter-list
                leaf REGULAR_EXPRESSION_ACCESS_LIST {
                    type string;
                }                  //AS_PATH_FILTER_NAME
                leaf all_prefix-list {
                    type enumeration {
                        enum all_prefix-list;
                    }
                }                  //prefix-list
                leaf PREFIX-LIST_NAME {
                    type string;
                }                  //WORD
                leaf all_access-list {
                    type enumeration {
                        enum all_access-list;
                    }
                }                  //access-list
                leaf ACCESS-LIST_NAME {
                    type string;
                }                  //ACCESSLIST_NAME
                leaf all_route-map {
                    type enumeration {
                        enum all_route-map;
                    }
                }                  //route-map
                leaf A_ROUTE-MAP_TO_MATCH {
                    type string;
                }                  //RMAP_NAME
                leaf all_rpki {
                    type enumeration {
                        enum all_rpki;
                    }
                }                  //rpki
                leaf CHOICE_CASE {
                    type enumeration {
                        enum invalid;
                        enum valid;
                        enum notfound;
                    }
                }                  //<invalid|valid|notfound> ['A valid path as determined by rpki', 'A invalid path as determined by rpki', 'A path that has no rpki data']
                leaf all_version {
                    type enumeration {
                        enum all_version;
                    }
                }                  //version
                leaf VERSION_NUMBER_AND_ABOVE {
                    type int32;
                }                  //(1-4294967295)
                leaf all_alias {
                    type enumeration {
                        enum all_alias;
                    }
                }                  //alias
                leaf BGP_COMMUNITY_ALIAS {
                    type string;
                }                  //ALIAS_NAME
                leaf all_wide {
                    type enumeration {
                        enum all_wide;
                    }
                }                  //wide
                leaf all_neighbors {
                    type enumeration {
                        enum all_neighbors;
                    }
                }                  //neighbors
                leaf IP_ADDRESS {
                    type union {
                        type inet:ipv4-address;
                        type inet:ipv6-address;
                        type string;
                    }
                }                  //<A.B.C.D|X:X::X:X|WORD>
                leaf BGP_NEIGHBOR_ROUTE_DIRECTION {
                    type enumeration {
                        enum advertised-routes;
                        enum received-routes;
                        enum filtered-routes;
                    }
                }                  //<advertised-routes|received-routes|filtered-routes> ['Display the routes advertised to a BGP neighbor', 'Display the received routes from neighbor', 'Display the filtered routes received from neighbor']
                leaf route-map {
                    type enumeration {
                        enum route-map;
                    }
                }                  //route-map
                leaf NAME_OF_THE_ROUTE {
                    type string;
                }                  //RMAP_NAME
                leaf detail {
                    type enumeration {
                        enum detail;
                    }
                }                  //detail
                leaf detail_json {
                    type enumeration {
                        enum detail_json;
                    }
                }                  //json
                leaf detail_wide {
                    type enumeration {
                        enum detail_wide;
                    }
                }                  //wide
                leaf cidr-only {
                    type enumeration {
                        enum cidr-only;
                    }
                }                  //cidr-only
                leaf cidr-only_wide {
                    type enumeration {
                        enum cidr-only_wide;
                    }
                }                  //wide
                leaf dampening {
                    type enumeration {
                        enum dampening;
                    }
                }                  //dampening
                leaf community {
                    type enumeration {
                        enum community;
                    }
                }                  //community
                leaf community_wide {
                    type enumeration {
                        enum community_wide;
                    }
                }                  //wide
                leaf community-list {
                    type enumeration {
                        enum community-list;
                    }
                }                  //community-list
                leaf filter-list {
                    type enumeration {
                        enum filter-list;
                    }
                }                  //filter-list
                leaf prefix-list {
                    type enumeration {
                        enum prefix-list;
                    }
                }                  //prefix-list
                leaf access-list {
                    type enumeration {
                        enum access-list;
                    }
                }                  //access-list
                leaf rpki {
                    type enumeration {
                        enum rpki;
                    }
                }                  //rpki
                leaf version {
                    type enumeration {
                        enum version;
                    }
                }                  //version
                leaf alias {
                    type enumeration {
                        enum alias;
                    }
                }                  //alias
                leaf IPV4_PREFIX {
                    type inet:ipv4-prefix;
                }                  //A.B.C.D/M
                leaf longer-prefixes {
                    type enumeration {
                        enum longer-prefixes;
                    }
                }                  //longer-prefixes
                leaf longer-prefixes_wide {
                    type enumeration {
                        enum longer-prefixes_wide;
                    }
                }                  //wide
                leaf longer-prefixes_json {
                    type enumeration {
                        enum longer-prefixes_json;
                    }
                }                  //longer-prefixes_json
                leaf longer-prefixes_json_detail {
                    type enumeration {
                        enum longer-prefixes_json_detail;
                    }
                }                  //detail
                leaf IPV6_PREFIX {
                    type inet:ipv6-prefix;
                }                  //X:X::X:X/M
                leaf detail-routes {
                    type enumeration {
                        enum detail-routes;
                    }
                }                  //detail-routes
                leaf detail-routes_wide {
                    type enumeration {
                        enum detail-routes_wide;
                    }
                }                  //wide
                leaf neighbors {
                    type enumeration {
                        enum neighbors;
                    }
                }                  //neighbors
                leaf BGP_NEIGHBOR_ROUTE_STATS {
                    type enumeration {
                        enum flap-statistics;
                        enum dampened-routes;
                        enum routes;
                    }
                }                  //<flap-statistics|dampened-routes|routes> ['Display flap statistics of the routes learned from neighbor', 'Display the dampened routes received from neighbor', 'Display routes learned from neighbor']
                leaf bestpath-routes {
                    type enumeration {
                        enum bestpath-routes;
                    }
                }                  //bestpath-routes
                leaf bestpath-routes_json {
                    type enumeration {
                        enum bestpath-routes_json;
                    }
                }                  //json
                leaf bestpath-routes_wide {
                    type enumeration {
                        enum bestpath-routes_wide;
                    }
                }                  //wide
                leaf received_prefix-filter {
                    type enumeration {
                        enum received_prefix-filter;
                    }
                }                  //received_prefix-filter
                leaf received_prefix-filter_json {
                    type enumeration {
                        enum received_prefix-filter_json;
                    }
                }                  //json
                leaf neighbors_json {
                    type enumeration {
                        enum neighbors_json;
                    }
                }                  //json
                leaf summary {
                    type enumeration {
                        enum summary;
                    }
                }                  //summary
                leaf summary_neighbor {
                    type enumeration {
                        enum summary_neighbor;
                    }
                }                  //neighbor
                leaf terse {
                    type enumeration {
                        enum terse;
                    }
                }                  //terse
                leaf terse_json {
                    type enumeration {
                        enum terse_json;
                    }
                }                  //json
                leaf wide_json {
                    type enumeration {
                        enum wide_json;
                    }
                }                  //json
                leaf terse_wide {
                    type enumeration {
                        enum terse_wide;
                    }
                }                  //terse_wide
                leaf terse_wide_json {
                    type enumeration {
                        enum terse_wide_json;
                    }
                }                  //json
                leaf summary_remote-as {
                    type enumeration {
                        enum summary_remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
                leaf summary_json {
                    type enumeration {
                        enum summary_json;
                    }
                }                  //json
                leaf large-community {
                    type enumeration {
                        enum large-community;
                    }
                }                  //large-community
                leaf LARGE_COMMUNITY {
                    type string;
                }                  //AA:BB:CC
                leaf large-community_json {
                    type enumeration {
                        enum large-community_json;
                    }
                }                  //json
                leaf large-community-list {
                    type enumeration {
                        enum large-community-list;
                    }
                }                  //large-community-list
                leaf LARGE-COMMUNITY-LIST_NUMBER {
                    type union {
                        type int32;
                        type string;
                    }
                }                  //<(1-500)|LCOMMUNITY_LIST_NAME>
                leaf regexp {
                    type enumeration {
                        enum regexp;
                    }
                }                  //regexp
                leaf REGULAR_EXPRESSION {
                    type string;
                }                  //REGEX
                leaf statistics {
                    type enumeration {
                        enum statistics;
                    }
                }                  //statistics
                leaf statistics_json {
                    type enumeration {
                        enum statistics_json;
                    }
                }                  //json
                leaf BGP_PATH_SELECTION {
                    type enumeration {
                        enum bestpath;
                        enum multipath;
                    }
                }                  //<bestpath|multipath> ['Display only the bestpath', 'Display only multipaths']
                leaf RPKI_VALIDATION_STATE {
                    type enumeration {
                        enum valid;
                        enum invalid;
                        enum notfound;
                    }
                }                  //<valid|invalid|notfound> ['A valid path as determined by rpki', 'A invalid path as determined by rpki', 'A path that has no rpki data']
                leaf unicast {
                    type enumeration {
                        enum unicast;
                    }
                }                  //unicast
                leaf unicast_community-list {
                    type enumeration {
                        enum unicast_community-list;
                    }
                }                  //community-list
                leaf unicast_filter-list {
                    type enumeration {
                        enum unicast_filter-list;
                    }
                }                  //filter-list
                leaf unicast_prefix-list {
                    type enumeration {
                        enum unicast_prefix-list;
                    }
                }                  //prefix-list
                leaf unicast_access-list {
                    type enumeration {
                        enum unicast_access-list;
                    }
                }                  //access-list
                leaf unicast_route-map {
                    type enumeration {
                        enum unicast_route-map;
                    }
                }                  //route-map
                leaf unicast_rpki {
                    type enumeration {
                        enum unicast_rpki;
                    }
                }                  //rpki
                leaf unicast_version {
                    type enumeration {
                        enum unicast_version;
                    }
                }                  //version
                leaf unicast_alias {
                    type enumeration {
                        enum unicast_alias;
                    }
                }                  //alias
                leaf unicast_wide {
                    type enumeration {
                        enum unicast_wide;
                    }
                }                  //wide
                leaf unicast_neighbors {
                    type enumeration {
                        enum unicast_neighbors;
                    }
                }                  //neighbors
                leaf unicast_large-community-list {
                    type enumeration {
                        enum unicast_large-community-list;
                    }
                }                  //large-community-list
                leaf unicast_regexp {
                    type enumeration {
                        enum unicast_regexp;
                    }
                }                  //regexp
                leaf flowspec {
                    type enumeration {
                        enum flowspec;
                    }
                }                  //flowspec
                leaf flowspec_community-list {
                    type enumeration {
                        enum flowspec_community-list;
                    }
                }                  //community-list
                leaf flowspec_filter-list {
                    type enumeration {
                        enum flowspec_filter-list;
                    }
                }                  //filter-list
                leaf flowspec_prefix-list {
                    type enumeration {
                        enum flowspec_prefix-list;
                    }
                }                  //prefix-list
                leaf flowspec_access-list {
                    type enumeration {
                        enum flowspec_access-list;
                    }
                }                  //access-list
                leaf flowspec_route-map {
                    type enumeration {
                        enum flowspec_route-map;
                    }
                }                  //route-map
                leaf flowspec_rpki {
                    type enumeration {
                        enum flowspec_rpki;
                    }
                }                  //rpki
                leaf flowspec_version {
                    type enumeration {
                        enum flowspec_version;
                    }
                }                  //version
                leaf flowspec_alias {
                    type enumeration {
                        enum flowspec_alias;
                    }
                }                  //alias
                leaf flowspec_wide {
                    type enumeration {
                        enum flowspec_wide;
                    }
                }                  //wide
                leaf flowspec_neighbors {
                    type enumeration {
                        enum flowspec_neighbors;
                    }
                }                  //neighbors
                leaf flowspec_large-community-list {
                    type enumeration {
                        enum flowspec_large-community-list;
                    }
                }                  //large-community-list
                leaf flowspec_regexp {
                    type enumeration {
                        enum flowspec_regexp;
                    }
                }                  //regexp
                leaf all_cidr-only {
                    type enumeration {
                        enum all_cidr-only;
                    }
                }                  //all_cidr-only
                leaf all_cidr-only_wide {
                    type enumeration {
                        enum all_cidr-only_wide;
                    }
                }                  //wide
                leaf all_dampening {
                    type enumeration {
                        enum all_dampening;
                    }
                }                  //all_dampening
                leaf all_community {
                    type enumeration {
                        enum all_community;
                    }
                }                  //all_community
                leaf all_community_wide {
                    type enumeration {
                        enum all_community_wide;
                    }
                }                  //wide
                leaf all_detail-routes {
                    type enumeration {
                        enum all_detail-routes;
                    }
                }                  //all_detail-routes
                leaf all_detail-routes_wide {
                    type enumeration {
                        enum all_detail-routes_wide;
                    }
                }                  //wide
                leaf all_json {
                    type enumeration {
                        enum all_json;
                    }
                }                  //all_json
                leaf all_json_detail {
                    type enumeration {
                        enum all_json_detail;
                    }
                }                  //detail
                leaf all_summary {
                    type enumeration {
                        enum all_summary;
                    }
                }                  //all_summary
                leaf all_summary_neighbor {
                    type enumeration {
                        enum all_summary_neighbor;
                    }
                }                  //neighbor
                leaf all_summary_remote-as {
                    type enumeration {
                        enum all_summary_remote-as;
                    }
                }                  //remote-as
                leaf all_summary_json {
                    type enumeration {
                        enum all_summary_json;
                    }
                }                  //json
                leaf cidr-only_json {
                    type enumeration {
                        enum cidr-only_json;
                    }
                }                  //cidr-only_json
                leaf cidr-only_json_detail {
                    type enumeration {
                        enum cidr-only_json_detail;
                    }
                }                  //detail
                leaf dampening_parameters {
                    type enumeration {
                        enum dampening_parameters;
                    }
                }                  //dampening_parameters
                leaf dampening_parameters_json {
                    type enumeration {
                        enum dampening_parameters_json;
                    }
                }                  //json
                leaf community_local-AS {
                    type enumeration {
                        enum community_local-AS;
                    }
                }                  //community_local-AS
                leaf community_local-AS_wide {
                    type enumeration {
                        enum community_local-AS_wide;
                    }
                }                  //wide
                leaf community_no-advertise {
                    type enumeration {
                        enum community_no-advertise;
                    }
                }                  //community_no-advertise
                leaf community_no-advertise_wide {
                    type enumeration {
                        enum community_no-advertise_wide;
                    }
                }                  //wide
                leaf community_no-export {
                    type enumeration {
                        enum community_no-export;
                    }
                }                  //community_no-export
                leaf community_no-export_wide {
                    type enumeration {
                        enum community_no-export_wide;
                    }
                }                  //wide
                leaf community_graceful-shutdown {
                    type enumeration {
                        enum community_graceful-shutdown;
                    }
                }                  //community_graceful-shutdown
                leaf community_graceful-shutdown_wide {
                    type enumeration {
                        enum community_graceful-shutdown_wide;
                    }
                }                  //wide
                leaf community_no-peer {
                    type enumeration {
                        enum community_no-peer;
                    }
                }                  //community_no-peer
                leaf community_no-peer_wide {
                    type enumeration {
                        enum community_no-peer_wide;
                    }
                }                  //wide
                leaf community_blackhole {
                    type enumeration {
                        enum community_blackhole;
                    }
                }                  //community_blackhole
                leaf community_blackhole_wide {
                    type enumeration {
                        enum community_blackhole_wide;
                    }
                }                  //wide
                leaf community_llgr-stale {
                    type enumeration {
                        enum community_llgr-stale;
                    }
                }                  //community_llgr-stale
                leaf community_llgr-stale_wide {
                    type enumeration {
                        enum community_llgr-stale_wide;
                    }
                }                  //wide
                leaf community_no-llgr {
                    type enumeration {
                        enum community_no-llgr;
                    }
                }                  //community_no-llgr
                leaf community_no-llgr_wide {
                    type enumeration {
                        enum community_no-llgr_wide;
                    }
                }                  //wide
                leaf community_accept-own {
                    type enumeration {
                        enum community_accept-own;
                    }
                }                  //community_accept-own
                leaf community_accept-own_wide {
                    type enumeration {
                        enum community_accept-own_wide;
                    }
                }                  //wide
                leaf community_accept-own-nexthop {
                    type enumeration {
                        enum community_accept-own-nexthop;
                    }
                }                  //community_accept-own-nexthop
                leaf community_accept-own-nexthop_wide {
                    type enumeration {
                        enum community_accept-own-nexthop_wide;
                    }
                }                  //wide
                leaf community_route-filter-v6 {
                    type enumeration {
                        enum community_route-filter-v6;
                    }
                }                  //community_route-filter-v6
                leaf community_route-filter-v6_wide {
                    type enumeration {
                        enum community_route-filter-v6_wide;
                    }
                }                  //wide
                leaf community_route-filter-v4 {
                    type enumeration {
                        enum community_route-filter-v4;
                    }
                }                  //community_route-filter-v4
                leaf community_route-filter-v4_wide {
                    type enumeration {
                        enum community_route-filter-v4_wide;
                    }
                }                  //wide
                leaf community_route-filter-translated-v6 {
                    type enumeration {
                        enum community_route-filter-translated-v6;
                    }
                }                  //community_route-filter-translated-v6
                leaf community_route-filter-translated-v6_wide {
                    type enumeration {
                        enum community_route-filter-translated-v6_wide;
                    }
                }                  //wide
                leaf community_route-filter-translated-v4 {
                    type enumeration {
                        enum community_route-filter-translated-v4;
                    }
                }                  //community_route-filter-translated-v4
                leaf community_route-filter-translated-v4_wide {
                    type enumeration {
                        enum community_route-filter-translated-v4_wide;
                    }
                }                  //wide
                leaf community_exact-match {
                    type enumeration {
                        enum community_exact-match;
                    }
                }                  //community_exact-match
                leaf community_exact-match_wide {
                    type enumeration {
                        enum community_exact-match_wide;
                    }
                }                  //wide
                leaf community_json {
                    type enumeration {
                        enum community_json;
                    }
                }                  //community_json
                leaf community_json_detail {
                    type enumeration {
                        enum community_json_detail;
                    }
                }                  //detail
                leaf detail-routes_json {
                    type enumeration {
                        enum detail-routes_json;
                    }
                }                  //detail-routes_json
                leaf detail-routes_json_detail {
                    type enumeration {
                        enum detail-routes_json_detail;
                    }
                }                  //detail
                leaf summary_established {
                    type enumeration {
                        enum summary_established;
                    }
                }                  //summary_established
                leaf summary_established_neighbor {
                    type enumeration {
                        enum summary_established_neighbor;
                    }
                }                  //neighbor
                leaf summary_established_remote-as {
                    type enumeration {
                        enum summary_established_remote-as;
                    }
                }                  //remote-as
                leaf summary_established_json {
                    type enumeration {
                        enum summary_established_json;
                    }
                }                  //json
                leaf summary_failed {
                    type enumeration {
                        enum summary_failed;
                    }
                }                  //summary_failed
                leaf summary_failed_neighbor {
                    type enumeration {
                        enum summary_failed_neighbor;
                    }
                }                  //neighbor
                leaf summary_failed_remote-as {
                    type enumeration {
                        enum summary_failed_remote-as;
                    }
                }                  //remote-as
                leaf summary_failed_json {
                    type enumeration {
                        enum summary_failed_json;
                    }
                }                  //json
                leaf summary_terse {
                    type enumeration {
                        enum summary_terse;
                    }
                }                  //summary_terse
                leaf summary_terse_json {
                    type enumeration {
                        enum summary_terse_json;
                    }
                }                  //json
                leaf summary_wide {
                    type enumeration {
                        enum summary_wide;
                    }
                }                  //summary_wide
                leaf summary_wide_json {
                    type enumeration {
                        enum summary_wide_json;
                    }
                }                  //json
                leaf all_cidr-only_json {
                    type enumeration {
                        enum all_cidr-only_json;
                    }
                }                  //all_cidr-only_json
                leaf all_cidr-only_json_detail {
                    type enumeration {
                        enum all_cidr-only_json_detail;
                    }
                }                  //detail
                leaf all_dampening_parameters {
                    type enumeration {
                        enum all_dampening_parameters;
                    }
                }                  //all_dampening_parameters
                leaf all_dampening_parameters_json {
                    type enumeration {
                        enum all_dampening_parameters_json;
                    }
                }                  //json
                leaf all_community_local-AS {
                    type enumeration {
                        enum all_community_local-AS;
                    }
                }                  //all_community_local-AS
                leaf all_community_local-AS_wide {
                    type enumeration {
                        enum all_community_local-AS_wide;
                    }
                }                  //wide
                leaf all_community_no-advertise {
                    type enumeration {
                        enum all_community_no-advertise;
                    }
                }                  //all_community_no-advertise
                leaf all_community_no-advertise_wide {
                    type enumeration {
                        enum all_community_no-advertise_wide;
                    }
                }                  //wide
                leaf all_community_no-export {
                    type enumeration {
                        enum all_community_no-export;
                    }
                }                  //all_community_no-export
                leaf all_community_no-export_wide {
                    type enumeration {
                        enum all_community_no-export_wide;
                    }
                }                  //wide
                leaf all_community_graceful-shutdown {
                    type enumeration {
                        enum all_community_graceful-shutdown;
                    }
                }                  //all_community_graceful-shutdown
                leaf all_community_graceful-shutdown_wide {
                    type enumeration {
                        enum all_community_graceful-shutdown_wide;
                    }
                }                  //wide
                leaf all_community_no-peer {
                    type enumeration {
                        enum all_community_no-peer;
                    }
                }                  //all_community_no-peer
                leaf all_community_no-peer_wide {
                    type enumeration {
                        enum all_community_no-peer_wide;
                    }
                }                  //wide
                leaf all_community_blackhole {
                    type enumeration {
                        enum all_community_blackhole;
                    }
                }                  //all_community_blackhole
                leaf all_community_blackhole_wide {
                    type enumeration {
                        enum all_community_blackhole_wide;
                    }
                }                  //wide
                leaf all_community_llgr-stale {
                    type enumeration {
                        enum all_community_llgr-stale;
                    }
                }                  //all_community_llgr-stale
                leaf all_community_llgr-stale_wide {
                    type enumeration {
                        enum all_community_llgr-stale_wide;
                    }
                }                  //wide
                leaf all_community_no-llgr {
                    type enumeration {
                        enum all_community_no-llgr;
                    }
                }                  //all_community_no-llgr
                leaf all_community_no-llgr_wide {
                    type enumeration {
                        enum all_community_no-llgr_wide;
                    }
                }                  //wide
                leaf all_community_accept-own {
                    type enumeration {
                        enum all_community_accept-own;
                    }
                }                  //all_community_accept-own
                leaf all_community_accept-own_wide {
                    type enumeration {
                        enum all_community_accept-own_wide;
                    }
                }                  //wide
                leaf all_community_accept-own-nexthop {
                    type enumeration {
                        enum all_community_accept-own-nexthop;
                    }
                }                  //all_community_accept-own-nexthop
                leaf all_community_accept-own-nexthop_wide {
                    type enumeration {
                        enum all_community_accept-own-nexthop_wide;
                    }
                }                  //wide
                leaf all_community_route-filter-v6 {
                    type enumeration {
                        enum all_community_route-filter-v6;
                    }
                }                  //all_community_route-filter-v6
                leaf all_community_route-filter-v6_wide {
                    type enumeration {
                        enum all_community_route-filter-v6_wide;
                    }
                }                  //wide
                leaf all_community_route-filter-v4 {
                    type enumeration {
                        enum all_community_route-filter-v4;
                    }
                }                  //all_community_route-filter-v4
                leaf all_community_route-filter-v4_wide {
                    type enumeration {
                        enum all_community_route-filter-v4_wide;
                    }
                }                  //wide
                leaf all_community_route-filter-translated-v6 {
                    type enumeration {
                        enum all_community_route-filter-translated-v6;
                    }
                }                  //all_community_route-filter-translated-v6
                leaf all_community_route-filter-translated-v6_wide {
                    type enumeration {
                        enum all_community_route-filter-translated-v6_wide;
                    }
                }                  //wide
                leaf all_community_route-filter-translated-v4 {
                    type enumeration {
                        enum all_community_route-filter-translated-v4;
                    }
                }                  //all_community_route-filter-translated-v4
                leaf all_community_route-filter-translated-v4_wide {
                    type enumeration {
                        enum all_community_route-filter-translated-v4_wide;
                    }
                }                  //wide
                leaf all_community_exact-match {
                    type enumeration {
                        enum all_community_exact-match;
                    }
                }                  //all_community_exact-match
                leaf all_community_exact-match_wide {
                    type enumeration {
                        enum all_community_exact-match_wide;
                    }
                }                  //wide
                leaf all_community_json {
                    type enumeration {
                        enum all_community_json;
                    }
                }                  //all_community_json
                leaf all_community_json_detail {
                    type enumeration {
                        enum all_community_json_detail;
                    }
                }                  //detail
                leaf all_detail-routes_json {
                    type enumeration {
                        enum all_detail-routes_json;
                    }
                }                  //all_detail-routes_json
                leaf all_detail-routes_json_detail {
                    type enumeration {
                        enum all_detail-routes_json_detail;
                    }
                }                  //detail
                leaf all_summary_established {
                    type enumeration {
                        enum all_summary_established;
                    }
                }                  //all_summary_established
                leaf all_summary_established_neighbor {
                    type enumeration {
                        enum all_summary_established_neighbor;
                    }
                }                  //neighbor
                leaf all_summary_established_remote-as {
                    type enumeration {
                        enum all_summary_established_remote-as;
                    }
                }                  //remote-as
                leaf all_summary_established_json {
                    type enumeration {
                        enum all_summary_established_json;
                    }
                }                  //json
                leaf all_summary_failed {
                    type enumeration {
                        enum all_summary_failed;
                    }
                }                  //all_summary_failed
                leaf all_summary_failed_neighbor {
                    type enumeration {
                        enum all_summary_failed_neighbor;
                    }
                }                  //neighbor
                leaf all_summary_failed_remote-as {
                    type enumeration {
                        enum all_summary_failed_remote-as;
                    }
                }                  //remote-as
                leaf all_summary_failed_json {
                    type enumeration {
                        enum all_summary_failed_json;
                    }
                }                  //json
                leaf all_summary_terse {
                    type enumeration {
                        enum all_summary_terse;
                    }
                }                  //all_summary_terse
                leaf all_summary_terse_json {
                    type enumeration {
                        enum all_summary_terse_json;
                    }
                }                  //json
                leaf all_summary_wide {
                    type enumeration {
                        enum all_summary_wide;
                    }
                }                  //all_summary_wide
                leaf all_summary_wide_json {
                    type enumeration {
                        enum all_summary_wide_json;
                    }
                }                  //json
                leaf community_local-AS_exact-match {
                    type enumeration {
                        enum community_local-AS_exact-match;
                    }
                }                  //community_local-AS_exact-match
                leaf community_local-AS_exact-match_wide {
                    type enumeration {
                        enum community_local-AS_exact-match_wide;
                    }
                }                  //wide
                leaf community_local-AS_json {
                    type enumeration {
                        enum community_local-AS_json;
                    }
                }                  //community_local-AS_json
                leaf community_local-AS_json_detail {
                    type enumeration {
                        enum community_local-AS_json_detail;
                    }
                }                  //detail
                leaf community_no-advertise_exact-match {
                    type enumeration {
                        enum community_no-advertise_exact-match;
                    }
                }                  //community_no-advertise_exact-match
                leaf community_no-advertise_exact-match_wide {
                    type enumeration {
                        enum community_no-advertise_exact-match_wide;
                    }
                }                  //wide
                leaf community_no-advertise_json {
                    type enumeration {
                        enum community_no-advertise_json;
                    }
                }                  //community_no-advertise_json
                leaf community_no-advertise_json_detail {
                    type enumeration {
                        enum community_no-advertise_json_detail;
                    }
                }                  //detail
                leaf community_no-export_exact-match {
                    type enumeration {
                        enum community_no-export_exact-match;
                    }
                }                  //community_no-export_exact-match
                leaf community_no-export_exact-match_wide {
                    type enumeration {
                        enum community_no-export_exact-match_wide;
                    }
                }                  //wide
                leaf community_no-export_json {
                    type enumeration {
                        enum community_no-export_json;
                    }
                }                  //community_no-export_json
                leaf community_no-export_json_detail {
                    type enumeration {
                        enum community_no-export_json_detail;
                    }
                }                  //detail
                leaf community_graceful-shutdown_exact-match {
                    type enumeration {
                        enum community_graceful-shutdown_exact-match;
                    }
                }                  //community_graceful-shutdown_exact-match
                leaf community_graceful-shutdown_exact-match_wide {
                    type enumeration {
                        enum community_graceful-shutdown_exact-match_wide;
                    }
                }                  //wide
                leaf community_graceful-shutdown_json {
                    type enumeration {
                        enum community_graceful-shutdown_json;
                    }
                }                  //community_graceful-shutdown_json
                leaf community_graceful-shutdown_json_detail {
                    type enumeration {
                        enum community_graceful-shutdown_json_detail;
                    }
                }                  //detail
                leaf community_no-peer_exact-match {
                    type enumeration {
                        enum community_no-peer_exact-match;
                    }
                }                  //community_no-peer_exact-match
                leaf community_no-peer_exact-match_wide {
                    type enumeration {
                        enum community_no-peer_exact-match_wide;
                    }
                }                  //wide
                leaf community_no-peer_json {
                    type enumeration {
                        enum community_no-peer_json;
                    }
                }                  //community_no-peer_json
                leaf community_no-peer_json_detail {
                    type enumeration {
                        enum community_no-peer_json_detail;
                    }
                }                  //detail
                leaf community_blackhole_exact-match {
                    type enumeration {
                        enum community_blackhole_exact-match;
                    }
                }                  //community_blackhole_exact-match
                leaf community_blackhole_exact-match_wide {
                    type enumeration {
                        enum community_blackhole_exact-match_wide;
                    }
                }                  //wide
                leaf community_blackhole_json {
                    type enumeration {
                        enum community_blackhole_json;
                    }
                }                  //community_blackhole_json
                leaf community_blackhole_json_detail {
                    type enumeration {
                        enum community_blackhole_json_detail;
                    }
                }                  //detail
                leaf community_llgr-stale_exact-match {
                    type enumeration {
                        enum community_llgr-stale_exact-match;
                    }
                }                  //community_llgr-stale_exact-match
                leaf community_llgr-stale_exact-match_wide {
                    type enumeration {
                        enum community_llgr-stale_exact-match_wide;
                    }
                }                  //wide
                leaf community_llgr-stale_json {
                    type enumeration {
                        enum community_llgr-stale_json;
                    }
                }                  //community_llgr-stale_json
                leaf community_llgr-stale_json_detail {
                    type enumeration {
                        enum community_llgr-stale_json_detail;
                    }
                }                  //detail
                leaf community_no-llgr_exact-match {
                    type enumeration {
                        enum community_no-llgr_exact-match;
                    }
                }                  //community_no-llgr_exact-match
                leaf community_no-llgr_exact-match_wide {
                    type enumeration {
                        enum community_no-llgr_exact-match_wide;
                    }
                }                  //wide
                leaf community_no-llgr_json {
                    type enumeration {
                        enum community_no-llgr_json;
                    }
                }                  //community_no-llgr_json
                leaf community_no-llgr_json_detail {
                    type enumeration {
                        enum community_no-llgr_json_detail;
                    }
                }                  //detail
                leaf community_accept-own_exact-match {
                    type enumeration {
                        enum community_accept-own_exact-match;
                    }
                }                  //community_accept-own_exact-match
                leaf community_accept-own_exact-match_wide {
                    type enumeration {
                        enum community_accept-own_exact-match_wide;
                    }
                }                  //wide
                leaf community_accept-own_json {
                    type enumeration {
                        enum community_accept-own_json;
                    }
                }                  //community_accept-own_json
                leaf community_accept-own_json_detail {
                    type enumeration {
                        enum community_accept-own_json_detail;
                    }
                }                  //detail
                leaf community_accept-own-nexthop_exact-match {
                    type enumeration {
                        enum community_accept-own-nexthop_exact-match;
                    }
                }                  //community_accept-own-nexthop_exact-match
                leaf community_accept-own-nexthop_exact-match_wide {
                    type enumeration {
                        enum community_accept-own-nexthop_exact-match_wide;
                    }
                }                  //wide
                leaf community_accept-own-nexthop_json {
                    type enumeration {
                        enum community_accept-own-nexthop_json;
                    }
                }                  //community_accept-own-nexthop_json
                leaf community_accept-own-nexthop_json_detail {
                    type enumeration {
                        enum community_accept-own-nexthop_json_detail;
                    }
                }                  //detail
                leaf community_route-filter-v6_exact-match {
                    type enumeration {
                        enum community_route-filter-v6_exact-match;
                    }
                }                  //community_route-filter-v6_exact-match
                leaf community_route-filter-v6_exact-match_wide {
                    type enumeration {
                        enum community_route-filter-v6_exact-match_wide;
                    }
                }                  //wide
                leaf community_route-filter-v6_json {
                    type enumeration {
                        enum community_route-filter-v6_json;
                    }
                }                  //community_route-filter-v6_json
                leaf community_route-filter-v6_json_detail {
                    type enumeration {
                        enum community_route-filter-v6_json_detail;
                    }
                }                  //detail
                leaf community_route-filter-v4_exact-match {
                    type enumeration {
                        enum community_route-filter-v4_exact-match;
                    }
                }                  //community_route-filter-v4_exact-match
                leaf community_route-filter-v4_exact-match_wide {
                    type enumeration {
                        enum community_route-filter-v4_exact-match_wide;
                    }
                }                  //wide
                leaf community_route-filter-v4_json {
                    type enumeration {
                        enum community_route-filter-v4_json;
                    }
                }                  //community_route-filter-v4_json
                leaf community_route-filter-v4_json_detail {
                    type enumeration {
                        enum community_route-filter-v4_json_detail;
                    }
                }                  //detail
                leaf community_route-filter-translated-v6_exact-match {
                    type enumeration {
                        enum community_route-filter-translated-v6_exact-match;
                    }
                }                  //community_route-filter-translated-v6_exact-match
                leaf community_route-filter-translated-v6_exact-match_wide {
                    type enumeration {
                        enum community_route-filter-translated-v6_exact-match_wide;
                    }
                }                  //wide
                leaf community_route-filter-translated-v6_json {
                    type enumeration {
                        enum community_route-filter-translated-v6_json;
                    }
                }                  //community_route-filter-translated-v6_json
                leaf community_route-filter-translated-v6_json_detail {
                    type enumeration {
                        enum community_route-filter-translated-v6_json_detail;
                    }
                }                  //detail
                leaf community_route-filter-translated-v4_exact-match {
                    type enumeration {
                        enum community_route-filter-translated-v4_exact-match;
                    }
                }                  //community_route-filter-translated-v4_exact-match
                leaf community_route-filter-translated-v4_exact-match_wide {
                    type enumeration {
                        enum community_route-filter-translated-v4_exact-match_wide;
                    }
                }                  //wide
                leaf community_route-filter-translated-v4_json {
                    type enumeration {
                        enum community_route-filter-translated-v4_json;
                    }
                }                  //community_route-filter-translated-v4_json
                leaf community_route-filter-translated-v4_json_detail {
                    type enumeration {
                        enum community_route-filter-translated-v4_json_detail;
                    }
                }                  //detail
                leaf community_exact-match_json {
                    type enumeration {
                        enum community_exact-match_json;
                    }
                }                  //community_exact-match_json
                leaf community_exact-match_json_detail {
                    type enumeration {
                        enum community_exact-match_json_detail;
                    }
                }                  //detail
                leaf summary_established_terse {
                    type enumeration {
                        enum summary_established_terse;
                    }
                }                  //summary_established_terse
                leaf summary_established_terse_json {
                    type enumeration {
                        enum summary_established_terse_json;
                    }
                }                  //json
                leaf summary_established_wide {
                    type enumeration {
                        enum summary_established_wide;
                    }
                }                  //summary_established_wide
                leaf summary_established_wide_json {
                    type enumeration {
                        enum summary_established_wide_json;
                    }
                }                  //json
                leaf summary_failed_terse {
                    type enumeration {
                        enum summary_failed_terse;
                    }
                }                  //summary_failed_terse
                leaf summary_failed_terse_json {
                    type enumeration {
                        enum summary_failed_terse_json;
                    }
                }                  //json
                leaf summary_failed_wide {
                    type enumeration {
                        enum summary_failed_wide;
                    }
                }                  //summary_failed_wide
                leaf summary_failed_wide_json {
                    type enumeration {
                        enum summary_failed_wide_json;
                    }
                }                  //json
                leaf summary_terse_wide {
                    type enumeration {
                        enum summary_terse_wide;
                    }
                }                  //summary_terse_wide
                leaf summary_terse_wide_json {
                    type enumeration {
                        enum summary_terse_wide_json;
                    }
                }                  //json
                leaf all_community_local-AS_exact-match {
                    type enumeration {
                        enum all_community_local-AS_exact-match;
                    }
                }                  //all_community_local-AS_exact-match
                leaf all_community_local-AS_exact-match_wide {
                    type enumeration {
                        enum all_community_local-AS_exact-match_wide;
                    }
                }                  //wide
                leaf all_community_local-AS_json {
                    type enumeration {
                        enum all_community_local-AS_json;
                    }
                }                  //all_community_local-AS_json
                leaf all_community_local-AS_json_detail {
                    type enumeration {
                        enum all_community_local-AS_json_detail;
                    }
                }                  //detail
                leaf all_community_no-advertise_exact-match {
                    type enumeration {
                        enum all_community_no-advertise_exact-match;
                    }
                }                  //all_community_no-advertise_exact-match
                leaf all_community_no-advertise_exact-match_wide {
                    type enumeration {
                        enum all_community_no-advertise_exact-match_wide;
                    }
                }                  //wide
                leaf all_community_no-advertise_json {
                    type enumeration {
                        enum all_community_no-advertise_json;
                    }
                }                  //all_community_no-advertise_json
                leaf all_community_no-advertise_json_detail {
                    type enumeration {
                        enum all_community_no-advertise_json_detail;
                    }
                }                  //detail
                leaf all_community_no-export_exact-match {
                    type enumeration {
                        enum all_community_no-export_exact-match;
                    }
                }                  //all_community_no-export_exact-match
                leaf all_community_no-export_exact-match_wide {
                    type enumeration {
                        enum all_community_no-export_exact-match_wide;
                    }
                }                  //wide
                leaf all_community_no-export_json {
                    type enumeration {
                        enum all_community_no-export_json;
                    }
                }                  //all_community_no-export_json
                leaf all_community_no-export_json_detail {
                    type enumeration {
                        enum all_community_no-export_json_detail;
                    }
                }                  //detail
                leaf all_community_graceful-shutdown_exact-match {
                    type enumeration {
                        enum all_community_graceful-shutdown_exact-match;
                    }
                }                  //all_community_graceful-shutdown_exact-match
                leaf all_community_graceful-shutdown_exact-match_wide {
                    type enumeration {
                        enum all_community_graceful-shutdown_exact-match_wide;
                    }
                }                  //wide
                leaf all_community_graceful-shutdown_json {
                    type enumeration {
                        enum all_community_graceful-shutdown_json;
                    }
                }                  //all_community_graceful-shutdown_json
                leaf all_community_graceful-shutdown_json_detail {
                    type enumeration {
                        enum all_community_graceful-shutdown_json_detail;
                    }
                }                  //detail
                leaf all_community_no-peer_exact-match {
                    type enumeration {
                        enum all_community_no-peer_exact-match;
                    }
                }                  //all_community_no-peer_exact-match
                leaf all_community_no-peer_exact-match_wide {
                    type enumeration {
                        enum all_community_no-peer_exact-match_wide;
                    }
                }                  //wide
                leaf all_community_no-peer_json {
                    type enumeration {
                        enum all_community_no-peer_json;
                    }
                }                  //all_community_no-peer_json
                leaf all_community_no-peer_json_detail {
                    type enumeration {
                        enum all_community_no-peer_json_detail;
                    }
                }                  //detail
                leaf all_community_blackhole_exact-match {
                    type enumeration {
                        enum all_community_blackhole_exact-match;
                    }
                }                  //all_community_blackhole_exact-match
                leaf all_community_blackhole_exact-match_wide {
                    type enumeration {
                        enum all_community_blackhole_exact-match_wide;
                    }
                }                  //wide
                leaf all_community_blackhole_json {
                    type enumeration {
                        enum all_community_blackhole_json;
                    }
                }                  //all_community_blackhole_json
                leaf all_community_blackhole_json_detail {
                    type enumeration {
                        enum all_community_blackhole_json_detail;
                    }
                }                  //detail
                leaf all_community_llgr-stale_exact-match {
                    type enumeration {
                        enum all_community_llgr-stale_exact-match;
                    }
                }                  //all_community_llgr-stale_exact-match
                leaf all_community_llgr-stale_exact-match_wide {
                    type enumeration {
                        enum all_community_llgr-stale_exact-match_wide;
                    }
                }                  //wide
                leaf all_community_llgr-stale_json {
                    type enumeration {
                        enum all_community_llgr-stale_json;
                    }
                }                  //all_community_llgr-stale_json
                leaf all_community_llgr-stale_json_detail {
                    type enumeration {
                        enum all_community_llgr-stale_json_detail;
                    }
                }                  //detail
                leaf all_community_no-llgr_exact-match {
                    type enumeration {
                        enum all_community_no-llgr_exact-match;
                    }
                }                  //all_community_no-llgr_exact-match
                leaf all_community_no-llgr_exact-match_wide {
                    type enumeration {
                        enum all_community_no-llgr_exact-match_wide;
                    }
                }                  //wide
                leaf all_community_no-llgr_json {
                    type enumeration {
                        enum all_community_no-llgr_json;
                    }
                }                  //all_community_no-llgr_json
                leaf all_community_no-llgr_json_detail {
                    type enumeration {
                        enum all_community_no-llgr_json_detail;
                    }
                }                  //detail
                leaf all_community_accept-own_exact-match {
                    type enumeration {
                        enum all_community_accept-own_exact-match;
                    }
                }                  //all_community_accept-own_exact-match
                leaf all_community_accept-own_exact-match_wide {
                    type enumeration {
                        enum all_community_accept-own_exact-match_wide;
                    }
                }                  //wide
                leaf all_community_accept-own_json {
                    type enumeration {
                        enum all_community_accept-own_json;
                    }
                }                  //all_community_accept-own_json
                leaf all_community_accept-own_json_detail {
                    type enumeration {
                        enum all_community_accept-own_json_detail;
                    }
                }                  //detail
                leaf all_community_accept-own-nexthop_exact-match {
                    type enumeration {
                        enum all_community_accept-own-nexthop_exact-match;
                    }
                }                  //all_community_accept-own-nexthop_exact-match
                leaf all_community_accept-own-nexthop_exact-match_wide {
                    type enumeration {
                        enum all_community_accept-own-nexthop_exact-match_wide;
                    }
                }                  //wide
                leaf all_community_accept-own-nexthop_json {
                    type enumeration {
                        enum all_community_accept-own-nexthop_json;
                    }
                }                  //all_community_accept-own-nexthop_json
                leaf all_community_accept-own-nexthop_json_detail {
                    type enumeration {
                        enum all_community_accept-own-nexthop_json_detail;
                    }
                }                  //detail
                leaf all_community_route-filter-v6_exact-match {
                    type enumeration {
                        enum all_community_route-filter-v6_exact-match;
                    }
                }                  //all_community_route-filter-v6_exact-match
                leaf all_community_route-filter-v6_exact-match_wide {
                    type enumeration {
                        enum all_community_route-filter-v6_exact-match_wide;
                    }
                }                  //wide
                leaf all_community_route-filter-v6_json {
                    type enumeration {
                        enum all_community_route-filter-v6_json;
                    }
                }                  //all_community_route-filter-v6_json
                leaf all_community_route-filter-v6_json_detail {
                    type enumeration {
                        enum all_community_route-filter-v6_json_detail;
                    }
                }                  //detail
                leaf all_community_route-filter-v4_exact-match {
                    type enumeration {
                        enum all_community_route-filter-v4_exact-match;
                    }
                }                  //all_community_route-filter-v4_exact-match
                leaf all_community_route-filter-v4_exact-match_wide {
                    type enumeration {
                        enum all_community_route-filter-v4_exact-match_wide;
                    }
                }                  //wide
                leaf all_community_route-filter-v4_json {
                    type enumeration {
                        enum all_community_route-filter-v4_json;
                    }
                }                  //all_community_route-filter-v4_json
                leaf all_community_route-filter-v4_json_detail {
                    type enumeration {
                        enum all_community_route-filter-v4_json_detail;
                    }
                }                  //detail
                leaf all_community_route-filter-translated-v6_exact-match {
                    type enumeration {
                        enum all_community_route-filter-translated-v6_exact-match;
                    }
                }                  //all_community_route-filter-translated-v6_exact-match
                leaf all_community_route-filter-translated-v6_exact-match_wide {
                    type enumeration {
                        enum all_community_route-filter-translated-v6_exact-match_wide;
                    }
                }                  //wide
                leaf all_community_route-filter-translated-v6_json {
                    type enumeration {
                        enum all_community_route-filter-translated-v6_json;
                    }
                }                  //all_community_route-filter-translated-v6_json
                leaf all_community_route-filter-translated-v6_json_detail {
                    type enumeration {
                        enum all_community_route-filter-translated-v6_json_detail;
                    }
                }                  //detail
                leaf all_community_route-filter-translated-v4_exact-match {
                    type enumeration {
                        enum all_community_route-filter-translated-v4_exact-match;
                    }
                }                  //all_community_route-filter-translated-v4_exact-match
                leaf all_community_route-filter-translated-v4_exact-match_wide {
                    type enumeration {
                        enum all_community_route-filter-translated-v4_exact-match_wide;
                    }
                }                  //wide
                leaf all_community_route-filter-translated-v4_json {
                    type enumeration {
                        enum all_community_route-filter-translated-v4_json;
                    }
                }                  //all_community_route-filter-translated-v4_json
                leaf all_community_route-filter-translated-v4_json_detail {
                    type enumeration {
                        enum all_community_route-filter-translated-v4_json_detail;
                    }
                }                  //detail
                leaf all_community_exact-match_json {
                    type enumeration {
                        enum all_community_exact-match_json;
                    }
                }                  //all_community_exact-match_json
                leaf all_community_exact-match_json_detail {
                    type enumeration {
                        enum all_community_exact-match_json_detail;
                    }
                }                  //detail
                leaf all_summary_established_terse {
                    type enumeration {
                        enum all_summary_established_terse;
                    }
                }                  //all_summary_established_terse
                leaf all_summary_established_terse_json {
                    type enumeration {
                        enum all_summary_established_terse_json;
                    }
                }                  //json
                leaf all_summary_established_wide {
                    type enumeration {
                        enum all_summary_established_wide;
                    }
                }                  //all_summary_established_wide
                leaf all_summary_established_wide_json {
                    type enumeration {
                        enum all_summary_established_wide_json;
                    }
                }                  //json
                leaf all_summary_failed_terse {
                    type enumeration {
                        enum all_summary_failed_terse;
                    }
                }                  //all_summary_failed_terse
                leaf all_summary_failed_terse_json {
                    type enumeration {
                        enum all_summary_failed_terse_json;
                    }
                }                  //json
                leaf all_summary_failed_wide {
                    type enumeration {
                        enum all_summary_failed_wide;
                    }
                }                  //all_summary_failed_wide
                leaf all_summary_failed_wide_json {
                    type enumeration {
                        enum all_summary_failed_wide_json;
                    }
                }                  //json
                leaf all_summary_terse_wide {
                    type enumeration {
                        enum all_summary_terse_wide;
                    }
                }                  //all_summary_terse_wide
                leaf all_summary_terse_wide_json {
                    type enumeration {
                        enum all_summary_terse_wide_json;
                    }
                }                  //json
                leaf community_local-AS_exact-match_json {
                    type enumeration {
                        enum community_local-AS_exact-match_json;
                    }
                }                  //community_local-AS_exact-match_json
                leaf community_local-AS_exact-match_json_detail {
                    type enumeration {
                        enum community_local-AS_exact-match_json_detail;
                    }
                }                  //detail
                leaf community_no-advertise_exact-match_json {
                    type enumeration {
                        enum community_no-advertise_exact-match_json;
                    }
                }                  //community_no-advertise_exact-match_json
                leaf community_no-advertise_exact-match_json_detail {
                    type enumeration {
                        enum community_no-advertise_exact-match_json_detail;
                    }
                }                  //detail
                leaf community_no-export_exact-match_json {
                    type enumeration {
                        enum community_no-export_exact-match_json;
                    }
                }                  //community_no-export_exact-match_json
                leaf community_no-export_exact-match_json_detail {
                    type enumeration {
                        enum community_no-export_exact-match_json_detail;
                    }
                }                  //detail
                leaf community_graceful-shutdown_exact-match_json {
                    type enumeration {
                        enum community_graceful-shutdown_exact-match_json;
                    }
                }                  //community_graceful-shutdown_exact-match_json
                leaf community_graceful-shutdown_exact-match_json_detail {
                    type enumeration {
                        enum community_graceful-shutdown_exact-match_json_detail;
                    }
                }                  //detail
                leaf community_no-peer_exact-match_json {
                    type enumeration {
                        enum community_no-peer_exact-match_json;
                    }
                }                  //community_no-peer_exact-match_json
                leaf community_no-peer_exact-match_json_detail {
                    type enumeration {
                        enum community_no-peer_exact-match_json_detail;
                    }
                }                  //detail
                leaf community_blackhole_exact-match_json {
                    type enumeration {
                        enum community_blackhole_exact-match_json;
                    }
                }                  //community_blackhole_exact-match_json
                leaf community_blackhole_exact-match_json_detail {
                    type enumeration {
                        enum community_blackhole_exact-match_json_detail;
                    }
                }                  //detail
                leaf community_llgr-stale_exact-match_json {
                    type enumeration {
                        enum community_llgr-stale_exact-match_json;
                    }
                }                  //community_llgr-stale_exact-match_json
                leaf community_llgr-stale_exact-match_json_detail {
                    type enumeration {
                        enum community_llgr-stale_exact-match_json_detail;
                    }
                }                  //detail
                leaf community_no-llgr_exact-match_json {
                    type enumeration {
                        enum community_no-llgr_exact-match_json;
                    }
                }                  //community_no-llgr_exact-match_json
                leaf community_no-llgr_exact-match_json_detail {
                    type enumeration {
                        enum community_no-llgr_exact-match_json_detail;
                    }
                }                  //detail
                leaf community_accept-own_exact-match_json {
                    type enumeration {
                        enum community_accept-own_exact-match_json;
                    }
                }                  //community_accept-own_exact-match_json
                leaf community_accept-own_exact-match_json_detail {
                    type enumeration {
                        enum community_accept-own_exact-match_json_detail;
                    }
                }                  //detail
                leaf community_accept-own-nexthop_exact-match_json {
                    type enumeration {
                        enum community_accept-own-nexthop_exact-match_json;
                    }
                }                  //community_accept-own-nexthop_exact-match_json
                leaf community_accept-own-nexthop_exact-match_json_detail {
                    type enumeration {
                        enum community_accept-own-nexthop_exact-match_json_detail;
                    }
                }                  //detail
                leaf community_route-filter-v6_exact-match_json {
                    type enumeration {
                        enum community_route-filter-v6_exact-match_json;
                    }
                }                  //community_route-filter-v6_exact-match_json
                leaf community_route-filter-v6_exact-match_json_detail {
                    type enumeration {
                        enum community_route-filter-v6_exact-match_json_detail;
                    }
                }                  //detail
                leaf community_route-filter-v4_exact-match_json {
                    type enumeration {
                        enum community_route-filter-v4_exact-match_json;
                    }
                }                  //community_route-filter-v4_exact-match_json
                leaf community_route-filter-v4_exact-match_json_detail {
                    type enumeration {
                        enum community_route-filter-v4_exact-match_json_detail;
                    }
                }                  //detail
                leaf community_route-filter-translated-v6_exact-match_json {
                    type enumeration {
                        enum community_route-filter-translated-v6_exact-match_json;
                    }
                }                  //community_route-filter-translated-v6_exact-match_json
                leaf community_route-filter-translated-v6_exact-match_json_detail {
                    type enumeration {
                        enum community_route-filter-translated-v6_exact-match_json_detail;
                    }
                }                  //detail
                leaf community_route-filter-translated-v4_exact-match_json {
                    type enumeration {
                        enum community_route-filter-translated-v4_exact-match_json;
                    }
                }                  //community_route-filter-translated-v4_exact-match_json
                leaf community_route-filter-translated-v4_exact-match_json_detail {
                    type enumeration {
                        enum community_route-filter-translated-v4_exact-match_json_detail;
                    }
                }                  //detail
                leaf summary_established_terse_wide {
                    type enumeration {
                        enum summary_established_terse_wide;
                    }
                }                  //summary_established_terse_wide
                leaf summary_established_terse_wide_json {
                    type enumeration {
                        enum summary_established_terse_wide_json;
                    }
                }                  //json
                leaf summary_failed_terse_wide {
                    type enumeration {
                        enum summary_failed_terse_wide;
                    }
                }                  //summary_failed_terse_wide
                leaf summary_failed_terse_wide_json {
                    type enumeration {
                        enum summary_failed_terse_wide_json;
                    }
                }                  //json
                leaf all_community_local-AS_exact-match_json {
                    type enumeration {
                        enum all_community_local-AS_exact-match_json;
                    }
                }                  //all_community_local-AS_exact-match_json
                leaf all_community_local-AS_exact-match_json_detail {
                    type enumeration {
                        enum all_community_local-AS_exact-match_json_detail;
                    }
                }                  //detail
                leaf all_community_no-advertise_exact-match_json {
                    type enumeration {
                        enum all_community_no-advertise_exact-match_json;
                    }
                }                  //all_community_no-advertise_exact-match_json
                leaf all_community_no-advertise_exact-match_json_detail {
                    type enumeration {
                        enum all_community_no-advertise_exact-match_json_detail;
                    }
                }                  //detail
                leaf all_community_no-export_exact-match_json {
                    type enumeration {
                        enum all_community_no-export_exact-match_json;
                    }
                }                  //all_community_no-export_exact-match_json
                leaf all_community_no-export_exact-match_json_detail {
                    type enumeration {
                        enum all_community_no-export_exact-match_json_detail;
                    }
                }                  //detail
                leaf all_community_graceful-shutdown_exact-match_json {
                    type enumeration {
                        enum all_community_graceful-shutdown_exact-match_json;
                    }
                }                  //all_community_graceful-shutdown_exact-match_json
                leaf all_community_graceful-shutdown_exact-match_json_detail {
                    type enumeration {
                        enum all_community_graceful-shutdown_exact-match_json_detail;
                    }
                }                  //detail
                leaf all_community_no-peer_exact-match_json {
                    type enumeration {
                        enum all_community_no-peer_exact-match_json;
                    }
                }                  //all_community_no-peer_exact-match_json
                leaf all_community_no-peer_exact-match_json_detail {
                    type enumeration {
                        enum all_community_no-peer_exact-match_json_detail;
                    }
                }                  //detail
                leaf all_community_blackhole_exact-match_json {
                    type enumeration {
                        enum all_community_blackhole_exact-match_json;
                    }
                }                  //all_community_blackhole_exact-match_json
                leaf all_community_blackhole_exact-match_json_detail {
                    type enumeration {
                        enum all_community_blackhole_exact-match_json_detail;
                    }
                }                  //detail
                leaf all_community_llgr-stale_exact-match_json {
                    type enumeration {
                        enum all_community_llgr-stale_exact-match_json;
                    }
                }                  //all_community_llgr-stale_exact-match_json
                leaf all_community_llgr-stale_exact-match_json_detail {
                    type enumeration {
                        enum all_community_llgr-stale_exact-match_json_detail;
                    }
                }                  //detail
                leaf all_community_no-llgr_exact-match_json {
                    type enumeration {
                        enum all_community_no-llgr_exact-match_json;
                    }
                }                  //all_community_no-llgr_exact-match_json
                leaf all_community_no-llgr_exact-match_json_detail {
                    type enumeration {
                        enum all_community_no-llgr_exact-match_json_detail;
                    }
                }                  //detail
                leaf all_community_accept-own_exact-match_json {
                    type enumeration {
                        enum all_community_accept-own_exact-match_json;
                    }
                }                  //all_community_accept-own_exact-match_json
                leaf all_community_accept-own_exact-match_json_detail {
                    type enumeration {
                        enum all_community_accept-own_exact-match_json_detail;
                    }
                }                  //detail
                leaf all_community_accept-own-nexthop_exact-match_json {
                    type enumeration {
                        enum all_community_accept-own-nexthop_exact-match_json;
                    }
                }                  //all_community_accept-own-nexthop_exact-match_json
                leaf all_community_accept-own-nexthop_exact-match_json_detail {
                    type enumeration {
                        enum all_community_accept-own-nexthop_exact-match_json_detail;
                    }
                }                  //detail
                leaf all_community_route-filter-v6_exact-match_json {
                    type enumeration {
                        enum all_community_route-filter-v6_exact-match_json;
                    }
                }                  //all_community_route-filter-v6_exact-match_json
                leaf all_community_route-filter-v6_exact-match_json_detail {
                    type enumeration {
                        enum all_community_route-filter-v6_exact-match_json_detail;
                    }
                }                  //detail
                leaf all_community_route-filter-v4_exact-match_json {
                    type enumeration {
                        enum all_community_route-filter-v4_exact-match_json;
                    }
                }                  //all_community_route-filter-v4_exact-match_json
                leaf all_community_route-filter-v4_exact-match_json_detail {
                    type enumeration {
                        enum all_community_route-filter-v4_exact-match_json_detail;
                    }
                }                  //detail
                leaf all_community_route-filter-translated-v6_exact-match_json {
                    type enumeration {
                        enum all_community_route-filter-translated-v6_exact-match_json;
                    }
                }                  //all_community_route-filter-translated-v6_exact-match_json
                leaf all_community_route-filter-translated-v6_exact-match_json_detail {
                    type enumeration {
                        enum all_community_route-filter-translated-v6_exact-match_json_detail;
                    }
                }                  //detail
                leaf all_community_route-filter-translated-v4_exact-match_json {
                    type enumeration {
                        enum all_community_route-filter-translated-v4_exact-match_json;
                    }
                }                  //all_community_route-filter-translated-v4_exact-match_json
                leaf all_community_route-filter-translated-v4_exact-match_json_detail {
                    type enumeration {
                        enum all_community_route-filter-translated-v4_exact-match_json_detail;
                    }
                }                  //detail
                leaf all_summary_established_terse_wide {
                    type enumeration {
                        enum all_summary_established_terse_wide;
                    }
                }                  //all_summary_established_terse_wide
                leaf all_summary_established_terse_wide_json {
                    type enumeration {
                        enum all_summary_established_terse_wide_json;
                    }
                }                  //json
                leaf all_summary_failed_terse_wide {
                    type enumeration {
                        enum all_summary_failed_terse_wide;
                    }
                }                  //all_summary_failed_terse_wide
                leaf all_summary_failed_terse_wide_json {
                    type enumeration {
                        enum all_summary_failed_terse_wide_json;
                    }
                }                  //json
                leaf unicast_all {
                    type enumeration {
                        enum unicast_all;
                    }
                }                  //unicast_all
                leaf unicast_all_community-list {
                    type enumeration {
                        enum unicast_all_community-list;
                    }
                }                  //community-list
                leaf unicast_all_filter-list {
                    type enumeration {
                        enum unicast_all_filter-list;
                    }
                }                  //filter-list
                leaf unicast_all_prefix-list {
                    type enumeration {
                        enum unicast_all_prefix-list;
                    }
                }                  //prefix-list
                leaf unicast_all_access-list {
                    type enumeration {
                        enum unicast_all_access-list;
                    }
                }                  //access-list
                leaf unicast_all_route-map {
                    type enumeration {
                        enum unicast_all_route-map;
                    }
                }                  //route-map
                leaf unicast_all_rpki {
                    type enumeration {
                        enum unicast_all_rpki;
                    }
                }                  //rpki
                leaf unicast_all_version {
                    type enumeration {
                        enum unicast_all_version;
                    }
                }                  //version
                leaf unicast_all_alias {
                    type enumeration {
                        enum unicast_all_alias;
                    }
                }                  //alias
                leaf unicast_all_wide {
                    type enumeration {
                        enum unicast_all_wide;
                    }
                }                  //wide
                leaf unicast_all_neighbors {
                    type enumeration {
                        enum unicast_all_neighbors;
                    }
                }                  //neighbors
                leaf unicast_cidr-only {
                    type enumeration {
                        enum unicast_cidr-only;
                    }
                }                  //unicast_cidr-only
                leaf unicast_cidr-only_wide {
                    type enumeration {
                        enum unicast_cidr-only_wide;
                    }
                }                  //wide
                leaf unicast_dampening {
                    type enumeration {
                        enum unicast_dampening;
                    }
                }                  //unicast_dampening
                leaf unicast_community {
                    type enumeration {
                        enum unicast_community;
                    }
                }                  //unicast_community
                leaf unicast_community_wide {
                    type enumeration {
                        enum unicast_community_wide;
                    }
                }                  //wide
                leaf unicast_detail-routes {
                    type enumeration {
                        enum unicast_detail-routes;
                    }
                }                  //unicast_detail-routes
                leaf unicast_detail-routes_wide {
                    type enumeration {
                        enum unicast_detail-routes_wide;
                    }
                }                  //wide
                leaf unicast_json {
                    type enumeration {
                        enum unicast_json;
                    }
                }                  //unicast_json
                leaf unicast_json_detail {
                    type enumeration {
                        enum unicast_json_detail;
                    }
                }                  //detail
                leaf unicast_summary {
                    type enumeration {
                        enum unicast_summary;
                    }
                }                  //unicast_summary
                leaf unicast_summary_neighbor {
                    type enumeration {
                        enum unicast_summary_neighbor;
                    }
                }                  //neighbor
                leaf unicast_summary_remote-as {
                    type enumeration {
                        enum unicast_summary_remote-as;
                    }
                }                  //remote-as
                leaf unicast_summary_json {
                    type enumeration {
                        enum unicast_summary_json;
                    }
                }                  //json
                leaf unicast_large-community {
                    type enumeration {
                        enum unicast_large-community;
                    }
                }                  //unicast_large-community
                leaf unicast_large-community_json {
                    type enumeration {
                        enum unicast_large-community_json;
                    }
                }                  //json
                leaf unicast_statistics {
                    type enumeration {
                        enum unicast_statistics;
                    }
                }                  //unicast_statistics
                leaf unicast_statistics_json {
                    type enumeration {
                        enum unicast_statistics_json;
                    }
                }                  //json
                leaf unicast_update-groups {
                    type enumeration {
                        enum unicast_update-groups;
                    }
                }                  //unicast_update-groups
                leaf unicast_update-groups_json {
                    type enumeration {
                        enum unicast_update-groups_json;
                    }
                }                  //json
                leaf flowspec_all {
                    type enumeration {
                        enum flowspec_all;
                    }
                }                  //flowspec_all
                leaf flowspec_all_community-list {
                    type enumeration {
                        enum flowspec_all_community-list;
                    }
                }                  //community-list
                leaf flowspec_all_filter-list {
                    type enumeration {
                        enum flowspec_all_filter-list;
                    }
                }                  //filter-list
                leaf flowspec_all_prefix-list {
                    type enumeration {
                        enum flowspec_all_prefix-list;
                    }
                }                  //prefix-list
                leaf flowspec_all_access-list {
                    type enumeration {
                        enum flowspec_all_access-list;
                    }
                }                  //access-list
                leaf flowspec_all_route-map {
                    type enumeration {
                        enum flowspec_all_route-map;
                    }
                }                  //route-map
                leaf flowspec_all_rpki {
                    type enumeration {
                        enum flowspec_all_rpki;
                    }
                }                  //rpki
                leaf flowspec_all_version {
                    type enumeration {
                        enum flowspec_all_version;
                    }
                }                  //version
                leaf flowspec_all_alias {
                    type enumeration {
                        enum flowspec_all_alias;
                    }
                }                  //alias
                leaf flowspec_all_wide {
                    type enumeration {
                        enum flowspec_all_wide;
                    }
                }                  //wide
                leaf flowspec_all_neighbors {
                    type enumeration {
                        enum flowspec_all_neighbors;
                    }
                }                  //neighbors
                leaf flowspec_cidr-only {
                    type enumeration {
                        enum flowspec_cidr-only;
                    }
                }                  //flowspec_cidr-only
                leaf flowspec_cidr-only_wide {
                    type enumeration {
                        enum flowspec_cidr-only_wide;
                    }
                }                  //wide
                leaf flowspec_dampening {
                    type enumeration {
                        enum flowspec_dampening;
                    }
                }                  //flowspec_dampening
                leaf flowspec_community {
                    type enumeration {
                        enum flowspec_community;
                    }
                }                  //flowspec_community
                leaf flowspec_community_wide {
                    type enumeration {
                        enum flowspec_community_wide;
                    }
                }                  //wide
                leaf flowspec_detail-routes {
                    type enumeration {
                        enum flowspec_detail-routes;
                    }
                }                  //flowspec_detail-routes
                leaf flowspec_detail-routes_wide {
                    type enumeration {
                        enum flowspec_detail-routes_wide;
                    }
                }                  //wide
                leaf flowspec_json {
                    type enumeration {
                        enum flowspec_json;
                    }
                }                  //flowspec_json
                leaf flowspec_json_detail {
                    type enumeration {
                        enum flowspec_json_detail;
                    }
                }                  //detail
                leaf flowspec_summary {
                    type enumeration {
                        enum flowspec_summary;
                    }
                }                  //flowspec_summary
                leaf flowspec_summary_neighbor {
                    type enumeration {
                        enum flowspec_summary_neighbor;
                    }
                }                  //neighbor
                leaf flowspec_summary_remote-as {
                    type enumeration {
                        enum flowspec_summary_remote-as;
                    }
                }                  //remote-as
                leaf flowspec_summary_json {
                    type enumeration {
                        enum flowspec_summary_json;
                    }
                }                  //json
                leaf flowspec_large-community {
                    type enumeration {
                        enum flowspec_large-community;
                    }
                }                  //flowspec_large-community
                leaf flowspec_large-community_json {
                    type enumeration {
                        enum flowspec_large-community_json;
                    }
                }                  //json
                leaf flowspec_statistics {
                    type enumeration {
                        enum flowspec_statistics;
                    }
                }                  //flowspec_statistics
                leaf flowspec_statistics_json {
                    type enumeration {
                        enum flowspec_statistics_json;
                    }
                }                  //json
                leaf flowspec_update-groups {
                    type enumeration {
                        enum flowspec_update-groups;
                    }
                }                  //flowspec_update-groups
                leaf flowspec_update-groups_json {
                    type enumeration {
                        enum flowspec_update-groups_json;
                    }
                }                  //json
                leaf flowspec_detail {
                    type enumeration {
                        enum flowspec_detail;
                    }
                }                  //flowspec_detail
                leaf flowspec_detail_json {
                    type enumeration {
                        enum flowspec_detail_json;
                    }
                }                  //json
                leaf unicast_all_cidr-only {
                    type enumeration {
                        enum unicast_all_cidr-only;
                    }
                }                  //unicast_all_cidr-only
                leaf unicast_all_cidr-only_wide {
                    type enumeration {
                        enum unicast_all_cidr-only_wide;
                    }
                }                  //wide
                leaf unicast_all_dampening {
                    type enumeration {
                        enum unicast_all_dampening;
                    }
                }                  //unicast_all_dampening
                leaf unicast_all_community {
                    type enumeration {
                        enum unicast_all_community;
                    }
                }                  //unicast_all_community
                leaf unicast_all_community_wide {
                    type enumeration {
                        enum unicast_all_community_wide;
                    }
                }                  //wide
                leaf unicast_all_detail-routes {
                    type enumeration {
                        enum unicast_all_detail-routes;
                    }
                }                  //unicast_all_detail-routes
                leaf unicast_all_detail-routes_wide {
                    type enumeration {
                        enum unicast_all_detail-routes_wide;
                    }
                }                  //wide
                leaf unicast_all_json {
                    type enumeration {
                        enum unicast_all_json;
                    }
                }                  //unicast_all_json
                leaf unicast_all_json_detail {
                    type enumeration {
                        enum unicast_all_json_detail;
                    }
                }                  //detail
                leaf unicast_all_summary {
                    type enumeration {
                        enum unicast_all_summary;
                    }
                }                  //unicast_all_summary
                leaf unicast_all_summary_neighbor {
                    type enumeration {
                        enum unicast_all_summary_neighbor;
                    }
                }                  //neighbor
                leaf unicast_all_summary_remote-as {
                    type enumeration {
                        enum unicast_all_summary_remote-as;
                    }
                }                  //remote-as
                leaf unicast_all_summary_json {
                    type enumeration {
                        enum unicast_all_summary_json;
                    }
                }                  //json
                leaf unicast_cidr-only_json {
                    type enumeration {
                        enum unicast_cidr-only_json;
                    }
                }                  //unicast_cidr-only_json
                leaf unicast_cidr-only_json_detail {
                    type enumeration {
                        enum unicast_cidr-only_json_detail;
                    }
                }                  //detail
                leaf unicast_dampening_parameters {
                    type enumeration {
                        enum unicast_dampening_parameters;
                    }
                }                  //unicast_dampening_parameters
                leaf unicast_dampening_parameters_json {
                    type enumeration {
                        enum unicast_dampening_parameters_json;
                    }
                }                  //json
                leaf unicast_community_local-AS {
                    type enumeration {
                        enum unicast_community_local-AS;
                    }
                }                  //unicast_community_local-AS
                leaf unicast_community_local-AS_wide {
                    type enumeration {
                        enum unicast_community_local-AS_wide;
                    }
                }                  //wide
                leaf unicast_community_no-advertise {
                    type enumeration {
                        enum unicast_community_no-advertise;
                    }
                }                  //unicast_community_no-advertise
                leaf unicast_community_no-advertise_wide {
                    type enumeration {
                        enum unicast_community_no-advertise_wide;
                    }
                }                  //wide
                leaf unicast_community_no-export {
                    type enumeration {
                        enum unicast_community_no-export;
                    }
                }                  //unicast_community_no-export
                leaf unicast_community_no-export_wide {
                    type enumeration {
                        enum unicast_community_no-export_wide;
                    }
                }                  //wide
                leaf unicast_community_graceful-shutdown {
                    type enumeration {
                        enum unicast_community_graceful-shutdown;
                    }
                }                  //unicast_community_graceful-shutdown
                leaf unicast_community_graceful-shutdown_wide {
                    type enumeration {
                        enum unicast_community_graceful-shutdown_wide;
                    }
                }                  //wide
                leaf unicast_community_no-peer {
                    type enumeration {
                        enum unicast_community_no-peer;
                    }
                }                  //unicast_community_no-peer
                leaf unicast_community_no-peer_wide {
                    type enumeration {
                        enum unicast_community_no-peer_wide;
                    }
                }                  //wide
                leaf unicast_community_blackhole {
                    type enumeration {
                        enum unicast_community_blackhole;
                    }
                }                  //unicast_community_blackhole
                leaf unicast_community_blackhole_wide {
                    type enumeration {
                        enum unicast_community_blackhole_wide;
                    }
                }                  //wide
                leaf unicast_community_llgr-stale {
                    type enumeration {
                        enum unicast_community_llgr-stale;
                    }
                }                  //unicast_community_llgr-stale
                leaf unicast_community_llgr-stale_wide {
                    type enumeration {
                        enum unicast_community_llgr-stale_wide;
                    }
                }                  //wide
                leaf unicast_community_no-llgr {
                    type enumeration {
                        enum unicast_community_no-llgr;
                    }
                }                  //unicast_community_no-llgr
                leaf unicast_community_no-llgr_wide {
                    type enumeration {
                        enum unicast_community_no-llgr_wide;
                    }
                }                  //wide
                leaf unicast_community_accept-own {
                    type enumeration {
                        enum unicast_community_accept-own;
                    }
                }                  //unicast_community_accept-own
                leaf unicast_community_accept-own_wide {
                    type enumeration {
                        enum unicast_community_accept-own_wide;
                    }
                }                  //wide
                leaf unicast_community_accept-own-nexthop {
                    type enumeration {
                        enum unicast_community_accept-own-nexthop;
                    }
                }                  //unicast_community_accept-own-nexthop
                leaf unicast_community_accept-own-nexthop_wide {
                    type enumeration {
                        enum unicast_community_accept-own-nexthop_wide;
                    }
                }                  //wide
                leaf unicast_community_route-filter-v6 {
                    type enumeration {
                        enum unicast_community_route-filter-v6;
                    }
                }                  //unicast_community_route-filter-v6
                leaf unicast_community_route-filter-v6_wide {
                    type enumeration {
                        enum unicast_community_route-filter-v6_wide;
                    }
                }                  //wide
                leaf unicast_community_route-filter-v4 {
                    type enumeration {
                        enum unicast_community_route-filter-v4;
                    }
                }                  //unicast_community_route-filter-v4
                leaf unicast_community_route-filter-v4_wide {
                    type enumeration {
                        enum unicast_community_route-filter-v4_wide;
                    }
                }                  //wide
                leaf unicast_community_route-filter-translated-v6 {
                    type enumeration {
                        enum unicast_community_route-filter-translated-v6;
                    }
                }                  //unicast_community_route-filter-translated-v6
                leaf unicast_community_route-filter-translated-v6_wide {
                    type enumeration {
                        enum unicast_community_route-filter-translated-v6_wide;
                    }
                }                  //wide
                leaf unicast_community_route-filter-translated-v4 {
                    type enumeration {
                        enum unicast_community_route-filter-translated-v4;
                    }
                }                  //unicast_community_route-filter-translated-v4
                leaf unicast_community_route-filter-translated-v4_wide {
                    type enumeration {
                        enum unicast_community_route-filter-translated-v4_wide;
                    }
                }                  //wide
                leaf unicast_community_exact-match {
                    type enumeration {
                        enum unicast_community_exact-match;
                    }
                }                  //unicast_community_exact-match
                leaf unicast_community_exact-match_wide {
                    type enumeration {
                        enum unicast_community_exact-match_wide;
                    }
                }                  //wide
                leaf unicast_community_json {
                    type enumeration {
                        enum unicast_community_json;
                    }
                }                  //unicast_community_json
                leaf unicast_community_json_detail {
                    type enumeration {
                        enum unicast_community_json_detail;
                    }
                }                  //detail
                leaf unicast_detail-routes_json {
                    type enumeration {
                        enum unicast_detail-routes_json;
                    }
                }                  //unicast_detail-routes_json
                leaf unicast_detail-routes_json_detail {
                    type enumeration {
                        enum unicast_detail-routes_json_detail;
                    }
                }                  //detail
                leaf unicast_summary_established {
                    type enumeration {
                        enum unicast_summary_established;
                    }
                }                  //unicast_summary_established
                leaf unicast_summary_established_neighbor {
                    type enumeration {
                        enum unicast_summary_established_neighbor;
                    }
                }                  //neighbor
                leaf unicast_summary_established_remote-as {
                    type enumeration {
                        enum unicast_summary_established_remote-as;
                    }
                }                  //remote-as
                leaf unicast_summary_established_json {
                    type enumeration {
                        enum unicast_summary_established_json;
                    }
                }                  //json
                leaf unicast_summary_failed {
                    type enumeration {
                        enum unicast_summary_failed;
                    }
                }                  //unicast_summary_failed
                leaf unicast_summary_failed_neighbor {
                    type enumeration {
                        enum unicast_summary_failed_neighbor;
                    }
                }                  //neighbor
                leaf unicast_summary_failed_remote-as {
                    type enumeration {
                        enum unicast_summary_failed_remote-as;
                    }
                }                  //remote-as
                leaf unicast_summary_failed_json {
                    type enumeration {
                        enum unicast_summary_failed_json;
                    }
                }                  //json
                leaf unicast_summary_terse {
                    type enumeration {
                        enum unicast_summary_terse;
                    }
                }                  //unicast_summary_terse
                leaf unicast_summary_terse_json {
                    type enumeration {
                        enum unicast_summary_terse_json;
                    }
                }                  //json
                leaf unicast_summary_wide {
                    type enumeration {
                        enum unicast_summary_wide;
                    }
                }                  //unicast_summary_wide
                leaf unicast_summary_wide_json {
                    type enumeration {
                        enum unicast_summary_wide_json;
                    }
                }                  //json
                leaf flowspec_all_cidr-only {
                    type enumeration {
                        enum flowspec_all_cidr-only;
                    }
                }                  //flowspec_all_cidr-only
                leaf flowspec_all_cidr-only_wide {
                    type enumeration {
                        enum flowspec_all_cidr-only_wide;
                    }
                }                  //wide
                leaf flowspec_all_dampening {
                    type enumeration {
                        enum flowspec_all_dampening;
                    }
                }                  //flowspec_all_dampening
                leaf flowspec_all_community {
                    type enumeration {
                        enum flowspec_all_community;
                    }
                }                  //flowspec_all_community
                leaf flowspec_all_community_wide {
                    type enumeration {
                        enum flowspec_all_community_wide;
                    }
                }                  //wide
                leaf flowspec_all_detail-routes {
                    type enumeration {
                        enum flowspec_all_detail-routes;
                    }
                }                  //flowspec_all_detail-routes
                leaf flowspec_all_detail-routes_wide {
                    type enumeration {
                        enum flowspec_all_detail-routes_wide;
                    }
                }                  //wide
                leaf flowspec_all_json {
                    type enumeration {
                        enum flowspec_all_json;
                    }
                }                  //flowspec_all_json
                leaf flowspec_all_json_detail {
                    type enumeration {
                        enum flowspec_all_json_detail;
                    }
                }                  //detail
                leaf flowspec_all_summary {
                    type enumeration {
                        enum flowspec_all_summary;
                    }
                }                  //flowspec_all_summary
                leaf flowspec_all_summary_neighbor {
                    type enumeration {
                        enum flowspec_all_summary_neighbor;
                    }
                }                  //neighbor
                leaf flowspec_all_summary_remote-as {
                    type enumeration {
                        enum flowspec_all_summary_remote-as;
                    }
                }                  //remote-as
                leaf flowspec_all_summary_json {
                    type enumeration {
                        enum flowspec_all_summary_json;
                    }
                }                  //json
                leaf flowspec_cidr-only_json {
                    type enumeration {
                        enum flowspec_cidr-only_json;
                    }
                }                  //flowspec_cidr-only_json
                leaf flowspec_cidr-only_json_detail {
                    type enumeration {
                        enum flowspec_cidr-only_json_detail;
                    }
                }                  //detail
                leaf flowspec_dampening_parameters {
                    type enumeration {
                        enum flowspec_dampening_parameters;
                    }
                }                  //flowspec_dampening_parameters
                leaf flowspec_dampening_parameters_json {
                    type enumeration {
                        enum flowspec_dampening_parameters_json;
                    }
                }                  //json
                leaf flowspec_community_local-AS {
                    type enumeration {
                        enum flowspec_community_local-AS;
                    }
                }                  //flowspec_community_local-AS
                leaf flowspec_community_local-AS_wide {
                    type enumeration {
                        enum flowspec_community_local-AS_wide;
                    }
                }                  //wide
                leaf flowspec_community_no-advertise {
                    type enumeration {
                        enum flowspec_community_no-advertise;
                    }
                }                  //flowspec_community_no-advertise
                leaf flowspec_community_no-advertise_wide {
                    type enumeration {
                        enum flowspec_community_no-advertise_wide;
                    }
                }                  //wide
                leaf flowspec_community_no-export {
                    type enumeration {
                        enum flowspec_community_no-export;
                    }
                }                  //flowspec_community_no-export
                leaf flowspec_community_no-export_wide {
                    type enumeration {
                        enum flowspec_community_no-export_wide;
                    }
                }                  //wide
                leaf flowspec_community_graceful-shutdown {
                    type enumeration {
                        enum flowspec_community_graceful-shutdown;
                    }
                }                  //flowspec_community_graceful-shutdown
                leaf flowspec_community_graceful-shutdown_wide {
                    type enumeration {
                        enum flowspec_community_graceful-shutdown_wide;
                    }
                }                  //wide
                leaf flowspec_community_no-peer {
                    type enumeration {
                        enum flowspec_community_no-peer;
                    }
                }                  //flowspec_community_no-peer
                leaf flowspec_community_no-peer_wide {
                    type enumeration {
                        enum flowspec_community_no-peer_wide;
                    }
                }                  //wide
                leaf flowspec_community_blackhole {
                    type enumeration {
                        enum flowspec_community_blackhole;
                    }
                }                  //flowspec_community_blackhole
                leaf flowspec_community_blackhole_wide {
                    type enumeration {
                        enum flowspec_community_blackhole_wide;
                    }
                }                  //wide
                leaf flowspec_community_llgr-stale {
                    type enumeration {
                        enum flowspec_community_llgr-stale;
                    }
                }                  //flowspec_community_llgr-stale
                leaf flowspec_community_llgr-stale_wide {
                    type enumeration {
                        enum flowspec_community_llgr-stale_wide;
                    }
                }                  //wide
                leaf flowspec_community_no-llgr {
                    type enumeration {
                        enum flowspec_community_no-llgr;
                    }
                }                  //flowspec_community_no-llgr
                leaf flowspec_community_no-llgr_wide {
                    type enumeration {
                        enum flowspec_community_no-llgr_wide;
                    }
                }                  //wide
                leaf flowspec_community_accept-own {
                    type enumeration {
                        enum flowspec_community_accept-own;
                    }
                }                  //flowspec_community_accept-own
                leaf flowspec_community_accept-own_wide {
                    type enumeration {
                        enum flowspec_community_accept-own_wide;
                    }
                }                  //wide
                leaf flowspec_community_accept-own-nexthop {
                    type enumeration {
                        enum flowspec_community_accept-own-nexthop;
                    }
                }                  //flowspec_community_accept-own-nexthop
                leaf flowspec_community_accept-own-nexthop_wide {
                    type enumeration {
                        enum flowspec_community_accept-own-nexthop_wide;
                    }
                }                  //wide
                leaf flowspec_community_route-filter-v6 {
                    type enumeration {
                        enum flowspec_community_route-filter-v6;
                    }
                }                  //flowspec_community_route-filter-v6
                leaf flowspec_community_route-filter-v6_wide {
                    type enumeration {
                        enum flowspec_community_route-filter-v6_wide;
                    }
                }                  //wide
                leaf flowspec_community_route-filter-v4 {
                    type enumeration {
                        enum flowspec_community_route-filter-v4;
                    }
                }                  //flowspec_community_route-filter-v4
                leaf flowspec_community_route-filter-v4_wide {
                    type enumeration {
                        enum flowspec_community_route-filter-v4_wide;
                    }
                }                  //wide
                leaf flowspec_community_route-filter-translated-v6 {
                    type enumeration {
                        enum flowspec_community_route-filter-translated-v6;
                    }
                }                  //flowspec_community_route-filter-translated-v6
                leaf flowspec_community_route-filter-translated-v6_wide {
                    type enumeration {
                        enum flowspec_community_route-filter-translated-v6_wide;
                    }
                }                  //wide
                leaf flowspec_community_route-filter-translated-v4 {
                    type enumeration {
                        enum flowspec_community_route-filter-translated-v4;
                    }
                }                  //flowspec_community_route-filter-translated-v4
                leaf flowspec_community_route-filter-translated-v4_wide {
                    type enumeration {
                        enum flowspec_community_route-filter-translated-v4_wide;
                    }
                }                  //wide
                leaf flowspec_community_exact-match {
                    type enumeration {
                        enum flowspec_community_exact-match;
                    }
                }                  //flowspec_community_exact-match
                leaf flowspec_community_exact-match_wide {
                    type enumeration {
                        enum flowspec_community_exact-match_wide;
                    }
                }                  //wide
                leaf flowspec_community_json {
                    type enumeration {
                        enum flowspec_community_json;
                    }
                }                  //flowspec_community_json
                leaf flowspec_community_json_detail {
                    type enumeration {
                        enum flowspec_community_json_detail;
                    }
                }                  //detail
                leaf flowspec_detail-routes_json {
                    type enumeration {
                        enum flowspec_detail-routes_json;
                    }
                }                  //flowspec_detail-routes_json
                leaf flowspec_detail-routes_json_detail {
                    type enumeration {
                        enum flowspec_detail-routes_json_detail;
                    }
                }                  //detail
                leaf flowspec_summary_established {
                    type enumeration {
                        enum flowspec_summary_established;
                    }
                }                  //flowspec_summary_established
                leaf flowspec_summary_established_neighbor {
                    type enumeration {
                        enum flowspec_summary_established_neighbor;
                    }
                }                  //neighbor
                leaf flowspec_summary_established_remote-as {
                    type enumeration {
                        enum flowspec_summary_established_remote-as;
                    }
                }                  //remote-as
                leaf flowspec_summary_established_json {
                    type enumeration {
                        enum flowspec_summary_established_json;
                    }
                }                  //json
                leaf flowspec_summary_failed {
                    type enumeration {
                        enum flowspec_summary_failed;
                    }
                }                  //flowspec_summary_failed
                leaf flowspec_summary_failed_neighbor {
                    type enumeration {
                        enum flowspec_summary_failed_neighbor;
                    }
                }                  //neighbor
                leaf flowspec_summary_failed_remote-as {
                    type enumeration {
                        enum flowspec_summary_failed_remote-as;
                    }
                }                  //remote-as
                leaf flowspec_summary_failed_json {
                    type enumeration {
                        enum flowspec_summary_failed_json;
                    }
                }                  //json
                leaf flowspec_summary_terse {
                    type enumeration {
                        enum flowspec_summary_terse;
                    }
                }                  //flowspec_summary_terse
                leaf flowspec_summary_terse_json {
                    type enumeration {
                        enum flowspec_summary_terse_json;
                    }
                }                  //json
                leaf flowspec_summary_wide {
                    type enumeration {
                        enum flowspec_summary_wide;
                    }
                }                  //flowspec_summary_wide
                leaf flowspec_summary_wide_json {
                    type enumeration {
                        enum flowspec_summary_wide_json;
                    }
                }                  //json
                leaf unicast_all_cidr-only_json {
                    type enumeration {
                        enum unicast_all_cidr-only_json;
                    }
                }                  //unicast_all_cidr-only_json
                leaf unicast_all_cidr-only_json_detail {
                    type enumeration {
                        enum unicast_all_cidr-only_json_detail;
                    }
                }                  //detail
                leaf unicast_all_dampening_parameters {
                    type enumeration {
                        enum unicast_all_dampening_parameters;
                    }
                }                  //unicast_all_dampening_parameters
                leaf unicast_all_dampening_parameters_json {
                    type enumeration {
                        enum unicast_all_dampening_parameters_json;
                    }
                }                  //json
                leaf unicast_all_community_local-AS {
                    type enumeration {
                        enum unicast_all_community_local-AS;
                    }
                }                  //unicast_all_community_local-AS
                leaf unicast_all_community_local-AS_wide {
                    type enumeration {
                        enum unicast_all_community_local-AS_wide;
                    }
                }                  //wide
                leaf unicast_all_community_no-advertise {
                    type enumeration {
                        enum unicast_all_community_no-advertise;
                    }
                }                  //unicast_all_community_no-advertise
                leaf unicast_all_community_no-advertise_wide {
                    type enumeration {
                        enum unicast_all_community_no-advertise_wide;
                    }
                }                  //wide
                leaf unicast_all_community_no-export {
                    type enumeration {
                        enum unicast_all_community_no-export;
                    }
                }                  //unicast_all_community_no-export
                leaf unicast_all_community_no-export_wide {
                    type enumeration {
                        enum unicast_all_community_no-export_wide;
                    }
                }                  //wide
                leaf unicast_all_community_graceful-shutdown {
                    type enumeration {
                        enum unicast_all_community_graceful-shutdown;
                    }
                }                  //unicast_all_community_graceful-shutdown
                leaf unicast_all_community_graceful-shutdown_wide {
                    type enumeration {
                        enum unicast_all_community_graceful-shutdown_wide;
                    }
                }                  //wide
                leaf unicast_all_community_no-peer {
                    type enumeration {
                        enum unicast_all_community_no-peer;
                    }
                }                  //unicast_all_community_no-peer
                leaf unicast_all_community_no-peer_wide {
                    type enumeration {
                        enum unicast_all_community_no-peer_wide;
                    }
                }                  //wide
                leaf unicast_all_community_blackhole {
                    type enumeration {
                        enum unicast_all_community_blackhole;
                    }
                }                  //unicast_all_community_blackhole
                leaf unicast_all_community_blackhole_wide {
                    type enumeration {
                        enum unicast_all_community_blackhole_wide;
                    }
                }                  //wide
                leaf unicast_all_community_llgr-stale {
                    type enumeration {
                        enum unicast_all_community_llgr-stale;
                    }
                }                  //unicast_all_community_llgr-stale
                leaf unicast_all_community_llgr-stale_wide {
                    type enumeration {
                        enum unicast_all_community_llgr-stale_wide;
                    }
                }                  //wide
                leaf unicast_all_community_no-llgr {
                    type enumeration {
                        enum unicast_all_community_no-llgr;
                    }
                }                  //unicast_all_community_no-llgr
                leaf unicast_all_community_no-llgr_wide {
                    type enumeration {
                        enum unicast_all_community_no-llgr_wide;
                    }
                }                  //wide
                leaf unicast_all_community_accept-own {
                    type enumeration {
                        enum unicast_all_community_accept-own;
                    }
                }                  //unicast_all_community_accept-own
                leaf unicast_all_community_accept-own_wide {
                    type enumeration {
                        enum unicast_all_community_accept-own_wide;
                    }
                }                  //wide
                leaf unicast_all_community_accept-own-nexthop {
                    type enumeration {
                        enum unicast_all_community_accept-own-nexthop;
                    }
                }                  //unicast_all_community_accept-own-nexthop
                leaf unicast_all_community_accept-own-nexthop_wide {
                    type enumeration {
                        enum unicast_all_community_accept-own-nexthop_wide;
                    }
                }                  //wide
                leaf unicast_all_community_route-filter-v6 {
                    type enumeration {
                        enum unicast_all_community_route-filter-v6;
                    }
                }                  //unicast_all_community_route-filter-v6
                leaf unicast_all_community_route-filter-v6_wide {
                    type enumeration {
                        enum unicast_all_community_route-filter-v6_wide;
                    }
                }                  //wide
                leaf unicast_all_community_route-filter-v4 {
                    type enumeration {
                        enum unicast_all_community_route-filter-v4;
                    }
                }                  //unicast_all_community_route-filter-v4
                leaf unicast_all_community_route-filter-v4_wide {
                    type enumeration {
                        enum unicast_all_community_route-filter-v4_wide;
                    }
                }                  //wide
                leaf unicast_all_community_route-filter-translated-v6 {
                    type enumeration {
                        enum unicast_all_community_route-filter-translated-v6;
                    }
                }                  //unicast_all_community_route-filter-translated-v6
                leaf unicast_all_community_route-filter-translated-v6_wide {
                    type enumeration {
                        enum unicast_all_community_route-filter-translated-v6_wide;
                    }
                }                  //wide
                leaf unicast_all_community_route-filter-translated-v4 {
                    type enumeration {
                        enum unicast_all_community_route-filter-translated-v4;
                    }
                }                  //unicast_all_community_route-filter-translated-v4
                leaf unicast_all_community_route-filter-translated-v4_wide {
                    type enumeration {
                        enum unicast_all_community_route-filter-translated-v4_wide;
                    }
                }                  //wide
                leaf unicast_all_community_exact-match {
                    type enumeration {
                        enum unicast_all_community_exact-match;
                    }
                }                  //unicast_all_community_exact-match
                leaf unicast_all_community_exact-match_wide {
                    type enumeration {
                        enum unicast_all_community_exact-match_wide;
                    }
                }                  //wide
                leaf unicast_all_community_json {
                    type enumeration {
                        enum unicast_all_community_json;
                    }
                }                  //unicast_all_community_json
                leaf unicast_all_community_json_detail {
                    type enumeration {
                        enum unicast_all_community_json_detail;
                    }
                }                  //detail
                leaf unicast_all_detail-routes_json {
                    type enumeration {
                        enum unicast_all_detail-routes_json;
                    }
                }                  //unicast_all_detail-routes_json
                leaf unicast_all_detail-routes_json_detail {
                    type enumeration {
                        enum unicast_all_detail-routes_json_detail;
                    }
                }                  //detail
                leaf unicast_all_summary_established {
                    type enumeration {
                        enum unicast_all_summary_established;
                    }
                }                  //unicast_all_summary_established
                leaf unicast_all_summary_established_neighbor {
                    type enumeration {
                        enum unicast_all_summary_established_neighbor;
                    }
                }                  //neighbor
                leaf unicast_all_summary_established_remote-as {
                    type enumeration {
                        enum unicast_all_summary_established_remote-as;
                    }
                }                  //remote-as
                leaf unicast_all_summary_established_json {
                    type enumeration {
                        enum unicast_all_summary_established_json;
                    }
                }                  //json
                leaf unicast_all_summary_failed {
                    type enumeration {
                        enum unicast_all_summary_failed;
                    }
                }                  //unicast_all_summary_failed
                leaf unicast_all_summary_failed_neighbor {
                    type enumeration {
                        enum unicast_all_summary_failed_neighbor;
                    }
                }                  //neighbor
                leaf unicast_all_summary_failed_remote-as {
                    type enumeration {
                        enum unicast_all_summary_failed_remote-as;
                    }
                }                  //remote-as
                leaf unicast_all_summary_failed_json {
                    type enumeration {
                        enum unicast_all_summary_failed_json;
                    }
                }                  //json
                leaf unicast_all_summary_terse {
                    type enumeration {
                        enum unicast_all_summary_terse;
                    }
                }                  //unicast_all_summary_terse
                leaf unicast_all_summary_terse_json {
                    type enumeration {
                        enum unicast_all_summary_terse_json;
                    }
                }                  //json
                leaf unicast_all_summary_wide {
                    type enumeration {
                        enum unicast_all_summary_wide;
                    }
                }                  //unicast_all_summary_wide
                leaf unicast_all_summary_wide_json {
                    type enumeration {
                        enum unicast_all_summary_wide_json;
                    }
                }                  //json
                leaf unicast_community_local-AS_exact-match {
                    type enumeration {
                        enum unicast_community_local-AS_exact-match;
                    }
                }                  //unicast_community_local-AS_exact-match
                leaf unicast_community_local-AS_exact-match_wide {
                    type enumeration {
                        enum unicast_community_local-AS_exact-match_wide;
                    }
                }                  //wide
                leaf unicast_community_local-AS_json {
                    type enumeration {
                        enum unicast_community_local-AS_json;
                    }
                }                  //unicast_community_local-AS_json
                leaf unicast_community_local-AS_json_detail {
                    type enumeration {
                        enum unicast_community_local-AS_json_detail;
                    }
                }                  //detail
                leaf unicast_community_no-advertise_exact-match {
                    type enumeration {
                        enum unicast_community_no-advertise_exact-match;
                    }
                }                  //unicast_community_no-advertise_exact-match
                leaf unicast_community_no-advertise_exact-match_wide {
                    type enumeration {
                        enum unicast_community_no-advertise_exact-match_wide;
                    }
                }                  //wide
                leaf unicast_community_no-advertise_json {
                    type enumeration {
                        enum unicast_community_no-advertise_json;
                    }
                }                  //unicast_community_no-advertise_json
                leaf unicast_community_no-advertise_json_detail {
                    type enumeration {
                        enum unicast_community_no-advertise_json_detail;
                    }
                }                  //detail
                leaf unicast_community_no-export_exact-match {
                    type enumeration {
                        enum unicast_community_no-export_exact-match;
                    }
                }                  //unicast_community_no-export_exact-match
                leaf unicast_community_no-export_exact-match_wide {
                    type enumeration {
                        enum unicast_community_no-export_exact-match_wide;
                    }
                }                  //wide
                leaf unicast_community_no-export_json {
                    type enumeration {
                        enum unicast_community_no-export_json;
                    }
                }                  //unicast_community_no-export_json
                leaf unicast_community_no-export_json_detail {
                    type enumeration {
                        enum unicast_community_no-export_json_detail;
                    }
                }                  //detail
                leaf unicast_community_graceful-shutdown_exact-match {
                    type enumeration {
                        enum unicast_community_graceful-shutdown_exact-match;
                    }
                }                  //unicast_community_graceful-shutdown_exact-match
                leaf unicast_community_graceful-shutdown_exact-match_wide {
                    type enumeration {
                        enum unicast_community_graceful-shutdown_exact-match_wide;
                    }
                }                  //wide
                leaf unicast_community_graceful-shutdown_json {
                    type enumeration {
                        enum unicast_community_graceful-shutdown_json;
                    }
                }                  //unicast_community_graceful-shutdown_json
                leaf unicast_community_graceful-shutdown_json_detail {
                    type enumeration {
                        enum unicast_community_graceful-shutdown_json_detail;
                    }
                }                  //detail
                leaf unicast_community_no-peer_exact-match {
                    type enumeration {
                        enum unicast_community_no-peer_exact-match;
                    }
                }                  //unicast_community_no-peer_exact-match
                leaf unicast_community_no-peer_exact-match_wide {
                    type enumeration {
                        enum unicast_community_no-peer_exact-match_wide;
                    }
                }                  //wide
                leaf unicast_community_no-peer_json {
                    type enumeration {
                        enum unicast_community_no-peer_json;
                    }
                }                  //unicast_community_no-peer_json
                leaf unicast_community_no-peer_json_detail {
                    type enumeration {
                        enum unicast_community_no-peer_json_detail;
                    }
                }                  //detail
                leaf unicast_community_blackhole_exact-match {
                    type enumeration {
                        enum unicast_community_blackhole_exact-match;
                    }
                }                  //unicast_community_blackhole_exact-match
                leaf unicast_community_blackhole_exact-match_wide {
                    type enumeration {
                        enum unicast_community_blackhole_exact-match_wide;
                    }
                }                  //wide
                leaf unicast_community_blackhole_json {
                    type enumeration {
                        enum unicast_community_blackhole_json;
                    }
                }                  //unicast_community_blackhole_json
                leaf unicast_community_blackhole_json_detail {
                    type enumeration {
                        enum unicast_community_blackhole_json_detail;
                    }
                }                  //detail
                leaf unicast_community_llgr-stale_exact-match {
                    type enumeration {
                        enum unicast_community_llgr-stale_exact-match;
                    }
                }                  //unicast_community_llgr-stale_exact-match
                leaf unicast_community_llgr-stale_exact-match_wide {
                    type enumeration {
                        enum unicast_community_llgr-stale_exact-match_wide;
                    }
                }                  //wide
                leaf unicast_community_llgr-stale_json {
                    type enumeration {
                        enum unicast_community_llgr-stale_json;
                    }
                }                  //unicast_community_llgr-stale_json
                leaf unicast_community_llgr-stale_json_detail {
                    type enumeration {
                        enum unicast_community_llgr-stale_json_detail;
                    }
                }                  //detail
                leaf unicast_community_no-llgr_exact-match {
                    type enumeration {
                        enum unicast_community_no-llgr_exact-match;
                    }
                }                  //unicast_community_no-llgr_exact-match
                leaf unicast_community_no-llgr_exact-match_wide {
                    type enumeration {
                        enum unicast_community_no-llgr_exact-match_wide;
                    }
                }                  //wide
                leaf unicast_community_no-llgr_json {
                    type enumeration {
                        enum unicast_community_no-llgr_json;
                    }
                }                  //unicast_community_no-llgr_json
                leaf unicast_community_no-llgr_json_detail {
                    type enumeration {
                        enum unicast_community_no-llgr_json_detail;
                    }
                }                  //detail
                leaf unicast_community_accept-own_exact-match {
                    type enumeration {
                        enum unicast_community_accept-own_exact-match;
                    }
                }                  //unicast_community_accept-own_exact-match
                leaf unicast_community_accept-own_exact-match_wide {
                    type enumeration {
                        enum unicast_community_accept-own_exact-match_wide;
                    }
                }                  //wide
                leaf unicast_community_accept-own_json {
                    type enumeration {
                        enum unicast_community_accept-own_json;
                    }
                }                  //unicast_community_accept-own_json
                leaf unicast_community_accept-own_json_detail {
                    type enumeration {
                        enum unicast_community_accept-own_json_detail;
                    }
                }                  //detail
                leaf unicast_community_accept-own-nexthop_exact-match {
                    type enumeration {
                        enum unicast_community_accept-own-nexthop_exact-match;
                    }
                }                  //unicast_community_accept-own-nexthop_exact-match
                leaf unicast_community_accept-own-nexthop_exact-match_wide {
                    type enumeration {
                        enum unicast_community_accept-own-nexthop_exact-match_wide;
                    }
                }                  //wide
                leaf unicast_community_accept-own-nexthop_json {
                    type enumeration {
                        enum unicast_community_accept-own-nexthop_json;
                    }
                }                  //unicast_community_accept-own-nexthop_json
                leaf unicast_community_accept-own-nexthop_json_detail {
                    type enumeration {
                        enum unicast_community_accept-own-nexthop_json_detail;
                    }
                }                  //detail
                leaf unicast_community_route-filter-v6_exact-match {
                    type enumeration {
                        enum unicast_community_route-filter-v6_exact-match;
                    }
                }                  //unicast_community_route-filter-v6_exact-match
                leaf unicast_community_route-filter-v6_exact-match_wide {
                    type enumeration {
                        enum unicast_community_route-filter-v6_exact-match_wide;
                    }
                }                  //wide
                leaf unicast_community_route-filter-v6_json {
                    type enumeration {
                        enum unicast_community_route-filter-v6_json;
                    }
                }                  //unicast_community_route-filter-v6_json
                leaf unicast_community_route-filter-v6_json_detail {
                    type enumeration {
                        enum unicast_community_route-filter-v6_json_detail;
                    }
                }                  //detail
                leaf unicast_community_route-filter-v4_exact-match {
                    type enumeration {
                        enum unicast_community_route-filter-v4_exact-match;
                    }
                }                  //unicast_community_route-filter-v4_exact-match
                leaf unicast_community_route-filter-v4_exact-match_wide {
                    type enumeration {
                        enum unicast_community_route-filter-v4_exact-match_wide;
                    }
                }                  //wide
                leaf unicast_community_route-filter-v4_json {
                    type enumeration {
                        enum unicast_community_route-filter-v4_json;
                    }
                }                  //unicast_community_route-filter-v4_json
                leaf unicast_community_route-filter-v4_json_detail {
                    type enumeration {
                        enum unicast_community_route-filter-v4_json_detail;
                    }
                }                  //detail
                leaf unicast_community_route-filter-translated-v6_exact-match {
                    type enumeration {
                        enum unicast_community_route-filter-translated-v6_exact-match;
                    }
                }                  //unicast_community_route-filter-translated-v6_exact-match
                leaf unicast_community_route-filter-translated-v6_exact-match_wide {
                    type enumeration {
                        enum unicast_community_route-filter-translated-v6_exact-match_wide;
                    }
                }                  //wide
                leaf unicast_community_route-filter-translated-v6_json {
                    type enumeration {
                        enum unicast_community_route-filter-translated-v6_json;
                    }
                }                  //unicast_community_route-filter-translated-v6_json
                leaf unicast_community_route-filter-translated-v6_json_detail {
                    type enumeration {
                        enum unicast_community_route-filter-translated-v6_json_detail;
                    }
                }                  //detail
                leaf unicast_community_route-filter-translated-v4_exact-match {
                    type enumeration {
                        enum unicast_community_route-filter-translated-v4_exact-match;
                    }
                }                  //unicast_community_route-filter-translated-v4_exact-match
                leaf unicast_community_route-filter-translated-v4_exact-match_wide {
                    type enumeration {
                        enum unicast_community_route-filter-translated-v4_exact-match_wide;
                    }
                }                  //wide
                leaf unicast_community_route-filter-translated-v4_json {
                    type enumeration {
                        enum unicast_community_route-filter-translated-v4_json;
                    }
                }                  //unicast_community_route-filter-translated-v4_json
                leaf unicast_community_route-filter-translated-v4_json_detail {
                    type enumeration {
                        enum unicast_community_route-filter-translated-v4_json_detail;
                    }
                }                  //detail
                leaf unicast_community_exact-match_json {
                    type enumeration {
                        enum unicast_community_exact-match_json;
                    }
                }                  //unicast_community_exact-match_json
                leaf unicast_community_exact-match_json_detail {
                    type enumeration {
                        enum unicast_community_exact-match_json_detail;
                    }
                }                  //detail
                leaf unicast_summary_established_terse {
                    type enumeration {
                        enum unicast_summary_established_terse;
                    }
                }                  //unicast_summary_established_terse
                leaf unicast_summary_established_terse_json {
                    type enumeration {
                        enum unicast_summary_established_terse_json;
                    }
                }                  //json
                leaf unicast_summary_established_wide {
                    type enumeration {
                        enum unicast_summary_established_wide;
                    }
                }                  //unicast_summary_established_wide
                leaf unicast_summary_established_wide_json {
                    type enumeration {
                        enum unicast_summary_established_wide_json;
                    }
                }                  //json
                leaf unicast_summary_failed_terse {
                    type enumeration {
                        enum unicast_summary_failed_terse;
                    }
                }                  //unicast_summary_failed_terse
                leaf unicast_summary_failed_terse_json {
                    type enumeration {
                        enum unicast_summary_failed_terse_json;
                    }
                }                  //json
                leaf unicast_summary_failed_wide {
                    type enumeration {
                        enum unicast_summary_failed_wide;
                    }
                }                  //unicast_summary_failed_wide
                leaf unicast_summary_failed_wide_json {
                    type enumeration {
                        enum unicast_summary_failed_wide_json;
                    }
                }                  //json
                leaf unicast_summary_terse_wide {
                    type enumeration {
                        enum unicast_summary_terse_wide;
                    }
                }                  //unicast_summary_terse_wide
                leaf unicast_summary_terse_wide_json {
                    type enumeration {
                        enum unicast_summary_terse_wide_json;
                    }
                }                  //json
                leaf flowspec_all_cidr-only_json {
                    type enumeration {
                        enum flowspec_all_cidr-only_json;
                    }
                }                  //flowspec_all_cidr-only_json
                leaf flowspec_all_cidr-only_json_detail {
                    type enumeration {
                        enum flowspec_all_cidr-only_json_detail;
                    }
                }                  //detail
                leaf flowspec_all_dampening_parameters {
                    type enumeration {
                        enum flowspec_all_dampening_parameters;
                    }
                }                  //flowspec_all_dampening_parameters
                leaf flowspec_all_dampening_parameters_json {
                    type enumeration {
                        enum flowspec_all_dampening_parameters_json;
                    }
                }                  //json
                leaf flowspec_all_community_local-AS {
                    type enumeration {
                        enum flowspec_all_community_local-AS;
                    }
                }                  //flowspec_all_community_local-AS
                leaf flowspec_all_community_local-AS_wide {
                    type enumeration {
                        enum flowspec_all_community_local-AS_wide;
                    }
                }                  //wide
                leaf flowspec_all_community_no-advertise {
                    type enumeration {
                        enum flowspec_all_community_no-advertise;
                    }
                }                  //flowspec_all_community_no-advertise
                leaf flowspec_all_community_no-advertise_wide {
                    type enumeration {
                        enum flowspec_all_community_no-advertise_wide;
                    }
                }                  //wide
                leaf flowspec_all_community_no-export {
                    type enumeration {
                        enum flowspec_all_community_no-export;
                    }
                }                  //flowspec_all_community_no-export
                leaf flowspec_all_community_no-export_wide {
                    type enumeration {
                        enum flowspec_all_community_no-export_wide;
                    }
                }                  //wide
                leaf flowspec_all_community_graceful-shutdown {
                    type enumeration {
                        enum flowspec_all_community_graceful-shutdown;
                    }
                }                  //flowspec_all_community_graceful-shutdown
                leaf flowspec_all_community_graceful-shutdown_wide {
                    type enumeration {
                        enum flowspec_all_community_graceful-shutdown_wide;
                    }
                }                  //wide
                leaf flowspec_all_community_no-peer {
                    type enumeration {
                        enum flowspec_all_community_no-peer;
                    }
                }                  //flowspec_all_community_no-peer
                leaf flowspec_all_community_no-peer_wide {
                    type enumeration {
                        enum flowspec_all_community_no-peer_wide;
                    }
                }                  //wide
                leaf flowspec_all_community_blackhole {
                    type enumeration {
                        enum flowspec_all_community_blackhole;
                    }
                }                  //flowspec_all_community_blackhole
                leaf flowspec_all_community_blackhole_wide {
                    type enumeration {
                        enum flowspec_all_community_blackhole_wide;
                    }
                }                  //wide
                leaf flowspec_all_community_llgr-stale {
                    type enumeration {
                        enum flowspec_all_community_llgr-stale;
                    }
                }                  //flowspec_all_community_llgr-stale
                leaf flowspec_all_community_llgr-stale_wide {
                    type enumeration {
                        enum flowspec_all_community_llgr-stale_wide;
                    }
                }                  //wide
                leaf flowspec_all_community_no-llgr {
                    type enumeration {
                        enum flowspec_all_community_no-llgr;
                    }
                }                  //flowspec_all_community_no-llgr
                leaf flowspec_all_community_no-llgr_wide {
                    type enumeration {
                        enum flowspec_all_community_no-llgr_wide;
                    }
                }                  //wide
                leaf flowspec_all_community_accept-own {
                    type enumeration {
                        enum flowspec_all_community_accept-own;
                    }
                }                  //flowspec_all_community_accept-own
                leaf flowspec_all_community_accept-own_wide {
                    type enumeration {
                        enum flowspec_all_community_accept-own_wide;
                    }
                }                  //wide
                leaf flowspec_all_community_accept-own-nexthop {
                    type enumeration {
                        enum flowspec_all_community_accept-own-nexthop;
                    }
                }                  //flowspec_all_community_accept-own-nexthop
                leaf flowspec_all_community_accept-own-nexthop_wide {
                    type enumeration {
                        enum flowspec_all_community_accept-own-nexthop_wide;
                    }
                }                  //wide
                leaf flowspec_all_community_route-filter-v6 {
                    type enumeration {
                        enum flowspec_all_community_route-filter-v6;
                    }
                }                  //flowspec_all_community_route-filter-v6
                leaf flowspec_all_community_route-filter-v6_wide {
                    type enumeration {
                        enum flowspec_all_community_route-filter-v6_wide;
                    }
                }                  //wide
                leaf flowspec_all_community_route-filter-v4 {
                    type enumeration {
                        enum flowspec_all_community_route-filter-v4;
                    }
                }                  //flowspec_all_community_route-filter-v4
                leaf flowspec_all_community_route-filter-v4_wide {
                    type enumeration {
                        enum flowspec_all_community_route-filter-v4_wide;
                    }
                }                  //wide
                leaf flowspec_all_community_route-filter-translated-v6 {
                    type enumeration {
                        enum flowspec_all_community_route-filter-translated-v6;
                    }
                }                  //flowspec_all_community_route-filter-translated-v6
                leaf flowspec_all_community_route-filter-translated-v6_wide {
                    type enumeration {
                        enum flowspec_all_community_route-filter-translated-v6_wide;
                    }
                }                  //wide
                leaf flowspec_all_community_route-filter-translated-v4 {
                    type enumeration {
                        enum flowspec_all_community_route-filter-translated-v4;
                    }
                }                  //flowspec_all_community_route-filter-translated-v4
                leaf flowspec_all_community_route-filter-translated-v4_wide {
                    type enumeration {
                        enum flowspec_all_community_route-filter-translated-v4_wide;
                    }
                }                  //wide
                leaf flowspec_all_community_exact-match {
                    type enumeration {
                        enum flowspec_all_community_exact-match;
                    }
                }                  //flowspec_all_community_exact-match
                leaf flowspec_all_community_exact-match_wide {
                    type enumeration {
                        enum flowspec_all_community_exact-match_wide;
                    }
                }                  //wide
                leaf flowspec_all_community_json {
                    type enumeration {
                        enum flowspec_all_community_json;
                    }
                }                  //flowspec_all_community_json
                leaf flowspec_all_community_json_detail {
                    type enumeration {
                        enum flowspec_all_community_json_detail;
                    }
                }                  //detail
                leaf flowspec_all_detail-routes_json {
                    type enumeration {
                        enum flowspec_all_detail-routes_json;
                    }
                }                  //flowspec_all_detail-routes_json
                leaf flowspec_all_detail-routes_json_detail {
                    type enumeration {
                        enum flowspec_all_detail-routes_json_detail;
                    }
                }                  //detail
                leaf flowspec_all_summary_established {
                    type enumeration {
                        enum flowspec_all_summary_established;
                    }
                }                  //flowspec_all_summary_established
                leaf flowspec_all_summary_established_neighbor {
                    type enumeration {
                        enum flowspec_all_summary_established_neighbor;
                    }
                }                  //neighbor
                leaf flowspec_all_summary_established_remote-as {
                    type enumeration {
                        enum flowspec_all_summary_established_remote-as;
                    }
                }                  //remote-as
                leaf flowspec_all_summary_established_json {
                    type enumeration {
                        enum flowspec_all_summary_established_json;
                    }
                }                  //json
                leaf flowspec_all_summary_failed {
                    type enumeration {
                        enum flowspec_all_summary_failed;
                    }
                }                  //flowspec_all_summary_failed
                leaf flowspec_all_summary_failed_neighbor {
                    type enumeration {
                        enum flowspec_all_summary_failed_neighbor;
                    }
                }                  //neighbor
                leaf flowspec_all_summary_failed_remote-as {
                    type enumeration {
                        enum flowspec_all_summary_failed_remote-as;
                    }
                }                  //remote-as
                leaf flowspec_all_summary_failed_json {
                    type enumeration {
                        enum flowspec_all_summary_failed_json;
                    }
                }                  //json
                leaf flowspec_all_summary_terse {
                    type enumeration {
                        enum flowspec_all_summary_terse;
                    }
                }                  //flowspec_all_summary_terse
                leaf flowspec_all_summary_terse_json {
                    type enumeration {
                        enum flowspec_all_summary_terse_json;
                    }
                }                  //json
                leaf flowspec_all_summary_wide {
                    type enumeration {
                        enum flowspec_all_summary_wide;
                    }
                }                  //flowspec_all_summary_wide
                leaf flowspec_all_summary_wide_json {
                    type enumeration {
                        enum flowspec_all_summary_wide_json;
                    }
                }                  //json
                leaf flowspec_community_local-AS_exact-match {
                    type enumeration {
                        enum flowspec_community_local-AS_exact-match;
                    }
                }                  //flowspec_community_local-AS_exact-match
                leaf flowspec_community_local-AS_exact-match_wide {
                    type enumeration {
                        enum flowspec_community_local-AS_exact-match_wide;
                    }
                }                  //wide
                leaf flowspec_community_local-AS_json {
                    type enumeration {
                        enum flowspec_community_local-AS_json;
                    }
                }                  //flowspec_community_local-AS_json
                leaf flowspec_community_local-AS_json_detail {
                    type enumeration {
                        enum flowspec_community_local-AS_json_detail;
                    }
                }                  //detail
                leaf flowspec_community_no-advertise_exact-match {
                    type enumeration {
                        enum flowspec_community_no-advertise_exact-match;
                    }
                }                  //flowspec_community_no-advertise_exact-match
                leaf flowspec_community_no-advertise_exact-match_wide {
                    type enumeration {
                        enum flowspec_community_no-advertise_exact-match_wide;
                    }
                }                  //wide
                leaf flowspec_community_no-advertise_json {
                    type enumeration {
                        enum flowspec_community_no-advertise_json;
                    }
                }                  //flowspec_community_no-advertise_json
                leaf flowspec_community_no-advertise_json_detail {
                    type enumeration {
                        enum flowspec_community_no-advertise_json_detail;
                    }
                }                  //detail
                leaf flowspec_community_no-export_exact-match {
                    type enumeration {
                        enum flowspec_community_no-export_exact-match;
                    }
                }                  //flowspec_community_no-export_exact-match
                leaf flowspec_community_no-export_exact-match_wide {
                    type enumeration {
                        enum flowspec_community_no-export_exact-match_wide;
                    }
                }                  //wide
                leaf flowspec_community_no-export_json {
                    type enumeration {
                        enum flowspec_community_no-export_json;
                    }
                }                  //flowspec_community_no-export_json
                leaf flowspec_community_no-export_json_detail {
                    type enumeration {
                        enum flowspec_community_no-export_json_detail;
                    }
                }                  //detail
                leaf flowspec_community_graceful-shutdown_exact-match {
                    type enumeration {
                        enum flowspec_community_graceful-shutdown_exact-match;
                    }
                }                  //flowspec_community_graceful-shutdown_exact-match
                leaf flowspec_community_graceful-shutdown_exact-match_wide {
                    type enumeration {
                        enum flowspec_community_graceful-shutdown_exact-match_wide;
                    }
                }                  //wide
                leaf flowspec_community_graceful-shutdown_json {
                    type enumeration {
                        enum flowspec_community_graceful-shutdown_json;
                    }
                }                  //flowspec_community_graceful-shutdown_json
                leaf flowspec_community_graceful-shutdown_json_detail {
                    type enumeration {
                        enum flowspec_community_graceful-shutdown_json_detail;
                    }
                }                  //detail
                leaf flowspec_community_no-peer_exact-match {
                    type enumeration {
                        enum flowspec_community_no-peer_exact-match;
                    }
                }                  //flowspec_community_no-peer_exact-match
                leaf flowspec_community_no-peer_exact-match_wide {
                    type enumeration {
                        enum flowspec_community_no-peer_exact-match_wide;
                    }
                }                  //wide
                leaf flowspec_community_no-peer_json {
                    type enumeration {
                        enum flowspec_community_no-peer_json;
                    }
                }                  //flowspec_community_no-peer_json
                leaf flowspec_community_no-peer_json_detail {
                    type enumeration {
                        enum flowspec_community_no-peer_json_detail;
                    }
                }                  //detail
                leaf flowspec_community_blackhole_exact-match {
                    type enumeration {
                        enum flowspec_community_blackhole_exact-match;
                    }
                }                  //flowspec_community_blackhole_exact-match
                leaf flowspec_community_blackhole_exact-match_wide {
                    type enumeration {
                        enum flowspec_community_blackhole_exact-match_wide;
                    }
                }                  //wide
                leaf flowspec_community_blackhole_json {
                    type enumeration {
                        enum flowspec_community_blackhole_json;
                    }
                }                  //flowspec_community_blackhole_json
                leaf flowspec_community_blackhole_json_detail {
                    type enumeration {
                        enum flowspec_community_blackhole_json_detail;
                    }
                }                  //detail
                leaf flowspec_community_llgr-stale_exact-match {
                    type enumeration {
                        enum flowspec_community_llgr-stale_exact-match;
                    }
                }                  //flowspec_community_llgr-stale_exact-match
                leaf flowspec_community_llgr-stale_exact-match_wide {
                    type enumeration {
                        enum flowspec_community_llgr-stale_exact-match_wide;
                    }
                }                  //wide
                leaf flowspec_community_llgr-stale_json {
                    type enumeration {
                        enum flowspec_community_llgr-stale_json;
                    }
                }                  //flowspec_community_llgr-stale_json
                leaf flowspec_community_llgr-stale_json_detail {
                    type enumeration {
                        enum flowspec_community_llgr-stale_json_detail;
                    }
                }                  //detail
                leaf flowspec_community_no-llgr_exact-match {
                    type enumeration {
                        enum flowspec_community_no-llgr_exact-match;
                    }
                }                  //flowspec_community_no-llgr_exact-match
                leaf flowspec_community_no-llgr_exact-match_wide {
                    type enumeration {
                        enum flowspec_community_no-llgr_exact-match_wide;
                    }
                }                  //wide
                leaf flowspec_community_no-llgr_json {
                    type enumeration {
                        enum flowspec_community_no-llgr_json;
                    }
                }                  //flowspec_community_no-llgr_json
                leaf flowspec_community_no-llgr_json_detail {
                    type enumeration {
                        enum flowspec_community_no-llgr_json_detail;
                    }
                }                  //detail
                leaf flowspec_community_accept-own_exact-match {
                    type enumeration {
                        enum flowspec_community_accept-own_exact-match;
                    }
                }                  //flowspec_community_accept-own_exact-match
                leaf flowspec_community_accept-own_exact-match_wide {
                    type enumeration {
                        enum flowspec_community_accept-own_exact-match_wide;
                    }
                }                  //wide
                leaf flowspec_community_accept-own_json {
                    type enumeration {
                        enum flowspec_community_accept-own_json;
                    }
                }                  //flowspec_community_accept-own_json
                leaf flowspec_community_accept-own_json_detail {
                    type enumeration {
                        enum flowspec_community_accept-own_json_detail;
                    }
                }                  //detail
                leaf flowspec_community_accept-own-nexthop_exact-match {
                    type enumeration {
                        enum flowspec_community_accept-own-nexthop_exact-match;
                    }
                }                  //flowspec_community_accept-own-nexthop_exact-match
                leaf flowspec_community_accept-own-nexthop_exact-match_wide {
                    type enumeration {
                        enum flowspec_community_accept-own-nexthop_exact-match_wide;
                    }
                }                  //wide
                leaf flowspec_community_accept-own-nexthop_json {
                    type enumeration {
                        enum flowspec_community_accept-own-nexthop_json;
                    }
                }                  //flowspec_community_accept-own-nexthop_json
                leaf flowspec_community_accept-own-nexthop_json_detail {
                    type enumeration {
                        enum flowspec_community_accept-own-nexthop_json_detail;
                    }
                }                  //detail
                leaf flowspec_community_route-filter-v6_exact-match {
                    type enumeration {
                        enum flowspec_community_route-filter-v6_exact-match;
                    }
                }                  //flowspec_community_route-filter-v6_exact-match
                leaf flowspec_community_route-filter-v6_exact-match_wide {
                    type enumeration {
                        enum flowspec_community_route-filter-v6_exact-match_wide;
                    }
                }                  //wide
                leaf flowspec_community_route-filter-v6_json {
                    type enumeration {
                        enum flowspec_community_route-filter-v6_json;
                    }
                }                  //flowspec_community_route-filter-v6_json
                leaf flowspec_community_route-filter-v6_json_detail {
                    type enumeration {
                        enum flowspec_community_route-filter-v6_json_detail;
                    }
                }                  //detail
                leaf flowspec_community_route-filter-v4_exact-match {
                    type enumeration {
                        enum flowspec_community_route-filter-v4_exact-match;
                    }
                }                  //flowspec_community_route-filter-v4_exact-match
                leaf flowspec_community_route-filter-v4_exact-match_wide {
                    type enumeration {
                        enum flowspec_community_route-filter-v4_exact-match_wide;
                    }
                }                  //wide
                leaf flowspec_community_route-filter-v4_json {
                    type enumeration {
                        enum flowspec_community_route-filter-v4_json;
                    }
                }                  //flowspec_community_route-filter-v4_json
                leaf flowspec_community_route-filter-v4_json_detail {
                    type enumeration {
                        enum flowspec_community_route-filter-v4_json_detail;
                    }
                }                  //detail
                leaf flowspec_community_route-filter-translated-v6_exact-match {
                    type enumeration {
                        enum flowspec_community_route-filter-translated-v6_exact-match;
                    }
                }                  //flowspec_community_route-filter-translated-v6_exact-match
                leaf flowspec_community_route-filter-translated-v6_exact-match_wide {
                    type enumeration {
                        enum flowspec_community_route-filter-translated-v6_exact-match_wide;
                    }
                }                  //wide
                leaf flowspec_community_route-filter-translated-v6_json {
                    type enumeration {
                        enum flowspec_community_route-filter-translated-v6_json;
                    }
                }                  //flowspec_community_route-filter-translated-v6_json
                leaf flowspec_community_route-filter-translated-v6_json_detail {
                    type enumeration {
                        enum flowspec_community_route-filter-translated-v6_json_detail;
                    }
                }                  //detail
                leaf flowspec_community_route-filter-translated-v4_exact-match {
                    type enumeration {
                        enum flowspec_community_route-filter-translated-v4_exact-match;
                    }
                }                  //flowspec_community_route-filter-translated-v4_exact-match
                leaf flowspec_community_route-filter-translated-v4_exact-match_wide {
                    type enumeration {
                        enum flowspec_community_route-filter-translated-v4_exact-match_wide;
                    }
                }                  //wide
                leaf flowspec_community_route-filter-translated-v4_json {
                    type enumeration {
                        enum flowspec_community_route-filter-translated-v4_json;
                    }
                }                  //flowspec_community_route-filter-translated-v4_json
                leaf flowspec_community_route-filter-translated-v4_json_detail {
                    type enumeration {
                        enum flowspec_community_route-filter-translated-v4_json_detail;
                    }
                }                  //detail
                leaf flowspec_community_exact-match_json {
                    type enumeration {
                        enum flowspec_community_exact-match_json;
                    }
                }                  //flowspec_community_exact-match_json
                leaf flowspec_community_exact-match_json_detail {
                    type enumeration {
                        enum flowspec_community_exact-match_json_detail;
                    }
                }                  //detail
                leaf flowspec_summary_established_terse {
                    type enumeration {
                        enum flowspec_summary_established_terse;
                    }
                }                  //flowspec_summary_established_terse
                leaf flowspec_summary_established_terse_json {
                    type enumeration {
                        enum flowspec_summary_established_terse_json;
                    }
                }                  //json
                leaf flowspec_summary_established_wide {
                    type enumeration {
                        enum flowspec_summary_established_wide;
                    }
                }                  //flowspec_summary_established_wide
                leaf flowspec_summary_established_wide_json {
                    type enumeration {
                        enum flowspec_summary_established_wide_json;
                    }
                }                  //json
                leaf flowspec_summary_failed_terse {
                    type enumeration {
                        enum flowspec_summary_failed_terse;
                    }
                }                  //flowspec_summary_failed_terse
                leaf flowspec_summary_failed_terse_json {
                    type enumeration {
                        enum flowspec_summary_failed_terse_json;
                    }
                }                  //json
                leaf flowspec_summary_failed_wide {
                    type enumeration {
                        enum flowspec_summary_failed_wide;
                    }
                }                  //flowspec_summary_failed_wide
                leaf flowspec_summary_failed_wide_json {
                    type enumeration {
                        enum flowspec_summary_failed_wide_json;
                    }
                }                  //json
                leaf flowspec_summary_terse_wide {
                    type enumeration {
                        enum flowspec_summary_terse_wide;
                    }
                }                  //flowspec_summary_terse_wide
                leaf flowspec_summary_terse_wide_json {
                    type enumeration {
                        enum flowspec_summary_terse_wide_json;
                    }
                }                  //json
                leaf unicast_all_community_local-AS_exact-match {
                    type enumeration {
                        enum unicast_all_community_local-AS_exact-match;
                    }
                }                  //unicast_all_community_local-AS_exact-match
                leaf unicast_all_community_local-AS_exact-match_wide {
                    type enumeration {
                        enum unicast_all_community_local-AS_exact-match_wide;
                    }
                }                  //wide
                leaf unicast_all_community_local-AS_json {
                    type enumeration {
                        enum unicast_all_community_local-AS_json;
                    }
                }                  //unicast_all_community_local-AS_json
                leaf unicast_all_community_local-AS_json_detail {
                    type enumeration {
                        enum unicast_all_community_local-AS_json_detail;
                    }
                }                  //detail
                leaf unicast_all_community_no-advertise_exact-match {
                    type enumeration {
                        enum unicast_all_community_no-advertise_exact-match;
                    }
                }                  //unicast_all_community_no-advertise_exact-match
                leaf unicast_all_community_no-advertise_exact-match_wide {
                    type enumeration {
                        enum unicast_all_community_no-advertise_exact-match_wide;
                    }
                }                  //wide
                leaf unicast_all_community_no-advertise_json {
                    type enumeration {
                        enum unicast_all_community_no-advertise_json;
                    }
                }                  //unicast_all_community_no-advertise_json
                leaf unicast_all_community_no-advertise_json_detail {
                    type enumeration {
                        enum unicast_all_community_no-advertise_json_detail;
                    }
                }                  //detail
                leaf unicast_all_community_no-export_exact-match {
                    type enumeration {
                        enum unicast_all_community_no-export_exact-match;
                    }
                }                  //unicast_all_community_no-export_exact-match
                leaf unicast_all_community_no-export_exact-match_wide {
                    type enumeration {
                        enum unicast_all_community_no-export_exact-match_wide;
                    }
                }                  //wide
                leaf unicast_all_community_no-export_json {
                    type enumeration {
                        enum unicast_all_community_no-export_json;
                    }
                }                  //unicast_all_community_no-export_json
                leaf unicast_all_community_no-export_json_detail {
                    type enumeration {
                        enum unicast_all_community_no-export_json_detail;
                    }
                }                  //detail
                leaf unicast_all_community_graceful-shutdown_exact-match {
                    type enumeration {
                        enum unicast_all_community_graceful-shutdown_exact-match;
                    }
                }                  //unicast_all_community_graceful-shutdown_exact-match
                leaf unicast_all_community_graceful-shutdown_exact-match_wide {
                    type enumeration {
                        enum unicast_all_community_graceful-shutdown_exact-match_wide;
                    }
                }                  //wide
                leaf unicast_all_community_graceful-shutdown_json {
                    type enumeration {
                        enum unicast_all_community_graceful-shutdown_json;
                    }
                }                  //unicast_all_community_graceful-shutdown_json
                leaf unicast_all_community_graceful-shutdown_json_detail {
                    type enumeration {
                        enum unicast_all_community_graceful-shutdown_json_detail;
                    }
                }                  //detail
                leaf unicast_all_community_no-peer_exact-match {
                    type enumeration {
                        enum unicast_all_community_no-peer_exact-match;
                    }
                }                  //unicast_all_community_no-peer_exact-match
                leaf unicast_all_community_no-peer_exact-match_wide {
                    type enumeration {
                        enum unicast_all_community_no-peer_exact-match_wide;
                    }
                }                  //wide
                leaf unicast_all_community_no-peer_json {
                    type enumeration {
                        enum unicast_all_community_no-peer_json;
                    }
                }                  //unicast_all_community_no-peer_json
                leaf unicast_all_community_no-peer_json_detail {
                    type enumeration {
                        enum unicast_all_community_no-peer_json_detail;
                    }
                }                  //detail
                leaf unicast_all_community_blackhole_exact-match {
                    type enumeration {
                        enum unicast_all_community_blackhole_exact-match;
                    }
                }                  //unicast_all_community_blackhole_exact-match
                leaf unicast_all_community_blackhole_exact-match_wide {
                    type enumeration {
                        enum unicast_all_community_blackhole_exact-match_wide;
                    }
                }                  //wide
                leaf unicast_all_community_blackhole_json {
                    type enumeration {
                        enum unicast_all_community_blackhole_json;
                    }
                }                  //unicast_all_community_blackhole_json
                leaf unicast_all_community_blackhole_json_detail {
                    type enumeration {
                        enum unicast_all_community_blackhole_json_detail;
                    }
                }                  //detail
                leaf unicast_all_community_llgr-stale_exact-match {
                    type enumeration {
                        enum unicast_all_community_llgr-stale_exact-match;
                    }
                }                  //unicast_all_community_llgr-stale_exact-match
                leaf unicast_all_community_llgr-stale_exact-match_wide {
                    type enumeration {
                        enum unicast_all_community_llgr-stale_exact-match_wide;
                    }
                }                  //wide
                leaf unicast_all_community_llgr-stale_json {
                    type enumeration {
                        enum unicast_all_community_llgr-stale_json;
                    }
                }                  //unicast_all_community_llgr-stale_json
                leaf unicast_all_community_llgr-stale_json_detail {
                    type enumeration {
                        enum unicast_all_community_llgr-stale_json_detail;
                    }
                }                  //detail
                leaf unicast_all_community_no-llgr_exact-match {
                    type enumeration {
                        enum unicast_all_community_no-llgr_exact-match;
                    }
                }                  //unicast_all_community_no-llgr_exact-match
                leaf unicast_all_community_no-llgr_exact-match_wide {
                    type enumeration {
                        enum unicast_all_community_no-llgr_exact-match_wide;
                    }
                }                  //wide
                leaf unicast_all_community_no-llgr_json {
                    type enumeration {
                        enum unicast_all_community_no-llgr_json;
                    }
                }                  //unicast_all_community_no-llgr_json
                leaf unicast_all_community_no-llgr_json_detail {
                    type enumeration {
                        enum unicast_all_community_no-llgr_json_detail;
                    }
                }                  //detail
                leaf unicast_all_community_accept-own_exact-match {
                    type enumeration {
                        enum unicast_all_community_accept-own_exact-match;
                    }
                }                  //unicast_all_community_accept-own_exact-match
                leaf unicast_all_community_accept-own_exact-match_wide {
                    type enumeration {
                        enum unicast_all_community_accept-own_exact-match_wide;
                    }
                }                  //wide
                leaf unicast_all_community_accept-own_json {
                    type enumeration {
                        enum unicast_all_community_accept-own_json;
                    }
                }                  //unicast_all_community_accept-own_json
                leaf unicast_all_community_accept-own_json_detail {
                    type enumeration {
                        enum unicast_all_community_accept-own_json_detail;
                    }
                }                  //detail
                leaf unicast_all_community_accept-own-nexthop_exact-match {
                    type enumeration {
                        enum unicast_all_community_accept-own-nexthop_exact-match;
                    }
                }                  //unicast_all_community_accept-own-nexthop_exact-match
                leaf unicast_all_community_accept-own-nexthop_exact-match_wide {
                    type enumeration {
                        enum unicast_all_community_accept-own-nexthop_exact-match_wide;
                    }
                }                  //wide
                leaf unicast_all_community_accept-own-nexthop_json {
                    type enumeration {
                        enum unicast_all_community_accept-own-nexthop_json;
                    }
                }                  //unicast_all_community_accept-own-nexthop_json
                leaf unicast_all_community_accept-own-nexthop_json_detail {
                    type enumeration {
                        enum unicast_all_community_accept-own-nexthop_json_detail;
                    }
                }                  //detail
                leaf unicast_all_community_route-filter-v6_exact-match {
                    type enumeration {
                        enum unicast_all_community_route-filter-v6_exact-match;
                    }
                }                  //unicast_all_community_route-filter-v6_exact-match
                leaf unicast_all_community_route-filter-v6_exact-match_wide {
                    type enumeration {
                        enum unicast_all_community_route-filter-v6_exact-match_wide;
                    }
                }                  //wide
                leaf unicast_all_community_route-filter-v6_json {
                    type enumeration {
                        enum unicast_all_community_route-filter-v6_json;
                    }
                }                  //unicast_all_community_route-filter-v6_json
                leaf unicast_all_community_route-filter-v6_json_detail {
                    type enumeration {
                        enum unicast_all_community_route-filter-v6_json_detail;
                    }
                }                  //detail
                leaf unicast_all_community_route-filter-v4_exact-match {
                    type enumeration {
                        enum unicast_all_community_route-filter-v4_exact-match;
                    }
                }                  //unicast_all_community_route-filter-v4_exact-match
                leaf unicast_all_community_route-filter-v4_exact-match_wide {
                    type enumeration {
                        enum unicast_all_community_route-filter-v4_exact-match_wide;
                    }
                }                  //wide
                leaf unicast_all_community_route-filter-v4_json {
                    type enumeration {
                        enum unicast_all_community_route-filter-v4_json;
                    }
                }                  //unicast_all_community_route-filter-v4_json
                leaf unicast_all_community_route-filter-v4_json_detail {
                    type enumeration {
                        enum unicast_all_community_route-filter-v4_json_detail;
                    }
                }                  //detail
                leaf unicast_all_community_route-filter-translated-v6_exact-match {
                    type enumeration {
                        enum unicast_all_community_route-filter-translated-v6_exact-match;
                    }
                }                  //unicast_all_community_route-filter-translated-v6_exact-match
                leaf unicast_all_community_route-filter-translated-v6_exact-match_wide {
                    type enumeration {
                        enum unicast_all_community_route-filter-translated-v6_exact-match_wide;
                    }
                }                  //wide
                leaf unicast_all_community_route-filter-translated-v6_json {
                    type enumeration {
                        enum unicast_all_community_route-filter-translated-v6_json;
                    }
                }                  //unicast_all_community_route-filter-translated-v6_json
                leaf unicast_all_community_route-filter-translated-v6_json_detail {
                    type enumeration {
                        enum unicast_all_community_route-filter-translated-v6_json_detail;
                    }
                }                  //detail
                leaf unicast_all_community_route-filter-translated-v4_exact-match {
                    type enumeration {
                        enum unicast_all_community_route-filter-translated-v4_exact-match;
                    }
                }                  //unicast_all_community_route-filter-translated-v4_exact-match
                leaf unicast_all_community_route-filter-translated-v4_exact-match_wide {
                    type enumeration {
                        enum unicast_all_community_route-filter-translated-v4_exact-match_wide;
                    }
                }                  //wide
                leaf unicast_all_community_route-filter-translated-v4_json {
                    type enumeration {
                        enum unicast_all_community_route-filter-translated-v4_json;
                    }
                }                  //unicast_all_community_route-filter-translated-v4_json
                leaf unicast_all_community_route-filter-translated-v4_json_detail {
                    type enumeration {
                        enum unicast_all_community_route-filter-translated-v4_json_detail;
                    }
                }                  //detail
                leaf unicast_all_community_exact-match_json {
                    type enumeration {
                        enum unicast_all_community_exact-match_json;
                    }
                }                  //unicast_all_community_exact-match_json
                leaf unicast_all_community_exact-match_json_detail {
                    type enumeration {
                        enum unicast_all_community_exact-match_json_detail;
                    }
                }                  //detail
                leaf unicast_all_summary_established_terse {
                    type enumeration {
                        enum unicast_all_summary_established_terse;
                    }
                }                  //unicast_all_summary_established_terse
                leaf unicast_all_summary_established_terse_json {
                    type enumeration {
                        enum unicast_all_summary_established_terse_json;
                    }
                }                  //json
                leaf unicast_all_summary_established_wide {
                    type enumeration {
                        enum unicast_all_summary_established_wide;
                    }
                }                  //unicast_all_summary_established_wide
                leaf unicast_all_summary_established_wide_json {
                    type enumeration {
                        enum unicast_all_summary_established_wide_json;
                    }
                }                  //json
                leaf unicast_all_summary_failed_terse {
                    type enumeration {
                        enum unicast_all_summary_failed_terse;
                    }
                }                  //unicast_all_summary_failed_terse
                leaf unicast_all_summary_failed_terse_json {
                    type enumeration {
                        enum unicast_all_summary_failed_terse_json;
                    }
                }                  //json
                leaf unicast_all_summary_failed_wide {
                    type enumeration {
                        enum unicast_all_summary_failed_wide;
                    }
                }                  //unicast_all_summary_failed_wide
                leaf unicast_all_summary_failed_wide_json {
                    type enumeration {
                        enum unicast_all_summary_failed_wide_json;
                    }
                }                  //json
                leaf unicast_all_summary_terse_wide {
                    type enumeration {
                        enum unicast_all_summary_terse_wide;
                    }
                }                  //unicast_all_summary_terse_wide
                leaf unicast_all_summary_terse_wide_json {
                    type enumeration {
                        enum unicast_all_summary_terse_wide_json;
                    }
                }                  //json
                leaf unicast_community_local-AS_exact-match_json {
                    type enumeration {
                        enum unicast_community_local-AS_exact-match_json;
                    }
                }                  //unicast_community_local-AS_exact-match_json
                leaf unicast_community_local-AS_exact-match_json_detail {
                    type enumeration {
                        enum unicast_community_local-AS_exact-match_json_detail;
                    }
                }                  //detail
                leaf unicast_community_no-advertise_exact-match_json {
                    type enumeration {
                        enum unicast_community_no-advertise_exact-match_json;
                    }
                }                  //unicast_community_no-advertise_exact-match_json
                leaf unicast_community_no-advertise_exact-match_json_detail {
                    type enumeration {
                        enum unicast_community_no-advertise_exact-match_json_detail;
                    }
                }                  //detail
                leaf unicast_community_no-export_exact-match_json {
                    type enumeration {
                        enum unicast_community_no-export_exact-match_json;
                    }
                }                  //unicast_community_no-export_exact-match_json
                leaf unicast_community_no-export_exact-match_json_detail {
                    type enumeration {
                        enum unicast_community_no-export_exact-match_json_detail;
                    }
                }                  //detail
                leaf unicast_community_graceful-shutdown_exact-match_json {
                    type enumeration {
                        enum unicast_community_graceful-shutdown_exact-match_json;
                    }
                }                  //unicast_community_graceful-shutdown_exact-match_json
                leaf unicast_community_graceful-shutdown_exact-match_json_detail {
                    type enumeration {
                        enum unicast_community_graceful-shutdown_exact-match_json_detail;
                    }
                }                  //detail
                leaf unicast_community_no-peer_exact-match_json {
                    type enumeration {
                        enum unicast_community_no-peer_exact-match_json;
                    }
                }                  //unicast_community_no-peer_exact-match_json
                leaf unicast_community_no-peer_exact-match_json_detail {
                    type enumeration {
                        enum unicast_community_no-peer_exact-match_json_detail;
                    }
                }                  //detail
                leaf unicast_community_blackhole_exact-match_json {
                    type enumeration {
                        enum unicast_community_blackhole_exact-match_json;
                    }
                }                  //unicast_community_blackhole_exact-match_json
                leaf unicast_community_blackhole_exact-match_json_detail {
                    type enumeration {
                        enum unicast_community_blackhole_exact-match_json_detail;
                    }
                }                  //detail
                leaf unicast_community_llgr-stale_exact-match_json {
                    type enumeration {
                        enum unicast_community_llgr-stale_exact-match_json;
                    }
                }                  //unicast_community_llgr-stale_exact-match_json
                leaf unicast_community_llgr-stale_exact-match_json_detail {
                    type enumeration {
                        enum unicast_community_llgr-stale_exact-match_json_detail;
                    }
                }                  //detail
                leaf unicast_community_no-llgr_exact-match_json {
                    type enumeration {
                        enum unicast_community_no-llgr_exact-match_json;
                    }
                }                  //unicast_community_no-llgr_exact-match_json
                leaf unicast_community_no-llgr_exact-match_json_detail {
                    type enumeration {
                        enum unicast_community_no-llgr_exact-match_json_detail;
                    }
                }                  //detail
                leaf unicast_community_accept-own_exact-match_json {
                    type enumeration {
                        enum unicast_community_accept-own_exact-match_json;
                    }
                }                  //unicast_community_accept-own_exact-match_json
                leaf unicast_community_accept-own_exact-match_json_detail {
                    type enumeration {
                        enum unicast_community_accept-own_exact-match_json_detail;
                    }
                }                  //detail
                leaf unicast_community_accept-own-nexthop_exact-match_json {
                    type enumeration {
                        enum unicast_community_accept-own-nexthop_exact-match_json;
                    }
                }                  //unicast_community_accept-own-nexthop_exact-match_json
                leaf unicast_community_accept-own-nexthop_exact-match_json_detail {
                    type enumeration {
                        enum unicast_community_accept-own-nexthop_exact-match_json_detail;
                    }
                }                  //detail
                leaf unicast_community_route-filter-v6_exact-match_json {
                    type enumeration {
                        enum unicast_community_route-filter-v6_exact-match_json;
                    }
                }                  //unicast_community_route-filter-v6_exact-match_json
                leaf unicast_community_route-filter-v6_exact-match_json_detail {
                    type enumeration {
                        enum unicast_community_route-filter-v6_exact-match_json_detail;
                    }
                }                  //detail
                leaf unicast_community_route-filter-v4_exact-match_json {
                    type enumeration {
                        enum unicast_community_route-filter-v4_exact-match_json;
                    }
                }                  //unicast_community_route-filter-v4_exact-match_json
                leaf unicast_community_route-filter-v4_exact-match_json_detail {
                    type enumeration {
                        enum unicast_community_route-filter-v4_exact-match_json_detail;
                    }
                }                  //detail
                leaf unicast_community_route-filter-translated-v6_exact-match_json {
                    type enumeration {
                        enum unicast_community_route-filter-translated-v6_exact-match_json;
                    }
                }                  //unicast_community_route-filter-translated-v6_exact-match_json
                leaf unicast_community_route-filter-translated-v6_exact-match_json_detail {
                    type enumeration {
                        enum unicast_community_route-filter-translated-v6_exact-match_json_detail;
                    }
                }                  //detail
                leaf unicast_community_route-filter-translated-v4_exact-match_json {
                    type enumeration {
                        enum unicast_community_route-filter-translated-v4_exact-match_json;
                    }
                }                  //unicast_community_route-filter-translated-v4_exact-match_json
                leaf unicast_community_route-filter-translated-v4_exact-match_json_detail {
                    type enumeration {
                        enum unicast_community_route-filter-translated-v4_exact-match_json_detail;
                    }
                }                  //detail
                leaf unicast_summary_established_terse_wide {
                    type enumeration {
                        enum unicast_summary_established_terse_wide;
                    }
                }                  //unicast_summary_established_terse_wide
                leaf unicast_summary_established_terse_wide_json {
                    type enumeration {
                        enum unicast_summary_established_terse_wide_json;
                    }
                }                  //json
                leaf unicast_summary_failed_terse_wide {
                    type enumeration {
                        enum unicast_summary_failed_terse_wide;
                    }
                }                  //unicast_summary_failed_terse_wide
                leaf unicast_summary_failed_terse_wide_json {
                    type enumeration {
                        enum unicast_summary_failed_terse_wide_json;
                    }
                }                  //json
                leaf flowspec_all_community_local-AS_exact-match {
                    type enumeration {
                        enum flowspec_all_community_local-AS_exact-match;
                    }
                }                  //flowspec_all_community_local-AS_exact-match
                leaf flowspec_all_community_local-AS_exact-match_wide {
                    type enumeration {
                        enum flowspec_all_community_local-AS_exact-match_wide;
                    }
                }                  //wide
                leaf flowspec_all_community_local-AS_json {
                    type enumeration {
                        enum flowspec_all_community_local-AS_json;
                    }
                }                  //flowspec_all_community_local-AS_json
                leaf flowspec_all_community_local-AS_json_detail {
                    type enumeration {
                        enum flowspec_all_community_local-AS_json_detail;
                    }
                }                  //detail
                leaf flowspec_all_community_no-advertise_exact-match {
                    type enumeration {
                        enum flowspec_all_community_no-advertise_exact-match;
                    }
                }                  //flowspec_all_community_no-advertise_exact-match
                leaf flowspec_all_community_no-advertise_exact-match_wide {
                    type enumeration {
                        enum flowspec_all_community_no-advertise_exact-match_wide;
                    }
                }                  //wide
                leaf flowspec_all_community_no-advertise_json {
                    type enumeration {
                        enum flowspec_all_community_no-advertise_json;
                    }
                }                  //flowspec_all_community_no-advertise_json
                leaf flowspec_all_community_no-advertise_json_detail {
                    type enumeration {
                        enum flowspec_all_community_no-advertise_json_detail;
                    }
                }                  //detail
                leaf flowspec_all_community_no-export_exact-match {
                    type enumeration {
                        enum flowspec_all_community_no-export_exact-match;
                    }
                }                  //flowspec_all_community_no-export_exact-match
                leaf flowspec_all_community_no-export_exact-match_wide {
                    type enumeration {
                        enum flowspec_all_community_no-export_exact-match_wide;
                    }
                }                  //wide
                leaf flowspec_all_community_no-export_json {
                    type enumeration {
                        enum flowspec_all_community_no-export_json;
                    }
                }                  //flowspec_all_community_no-export_json
                leaf flowspec_all_community_no-export_json_detail {
                    type enumeration {
                        enum flowspec_all_community_no-export_json_detail;
                    }
                }                  //detail
                leaf flowspec_all_community_graceful-shutdown_exact-match {
                    type enumeration {
                        enum flowspec_all_community_graceful-shutdown_exact-match;
                    }
                }                  //flowspec_all_community_graceful-shutdown_exact-match
                leaf flowspec_all_community_graceful-shutdown_exact-match_wide {
                    type enumeration {
                        enum flowspec_all_community_graceful-shutdown_exact-match_wide;
                    }
                }                  //wide
                leaf flowspec_all_community_graceful-shutdown_json {
                    type enumeration {
                        enum flowspec_all_community_graceful-shutdown_json;
                    }
                }                  //flowspec_all_community_graceful-shutdown_json
                leaf flowspec_all_community_graceful-shutdown_json_detail {
                    type enumeration {
                        enum flowspec_all_community_graceful-shutdown_json_detail;
                    }
                }                  //detail
                leaf flowspec_all_community_no-peer_exact-match {
                    type enumeration {
                        enum flowspec_all_community_no-peer_exact-match;
                    }
                }                  //flowspec_all_community_no-peer_exact-match
                leaf flowspec_all_community_no-peer_exact-match_wide {
                    type enumeration {
                        enum flowspec_all_community_no-peer_exact-match_wide;
                    }
                }                  //wide
                leaf flowspec_all_community_no-peer_json {
                    type enumeration {
                        enum flowspec_all_community_no-peer_json;
                    }
                }                  //flowspec_all_community_no-peer_json
                leaf flowspec_all_community_no-peer_json_detail {
                    type enumeration {
                        enum flowspec_all_community_no-peer_json_detail;
                    }
                }                  //detail
                leaf flowspec_all_community_blackhole_exact-match {
                    type enumeration {
                        enum flowspec_all_community_blackhole_exact-match;
                    }
                }                  //flowspec_all_community_blackhole_exact-match
                leaf flowspec_all_community_blackhole_exact-match_wide {
                    type enumeration {
                        enum flowspec_all_community_blackhole_exact-match_wide;
                    }
                }                  //wide
                leaf flowspec_all_community_blackhole_json {
                    type enumeration {
                        enum flowspec_all_community_blackhole_json;
                    }
                }                  //flowspec_all_community_blackhole_json
                leaf flowspec_all_community_blackhole_json_detail {
                    type enumeration {
                        enum flowspec_all_community_blackhole_json_detail;
                    }
                }                  //detail
                leaf flowspec_all_community_llgr-stale_exact-match {
                    type enumeration {
                        enum flowspec_all_community_llgr-stale_exact-match;
                    }
                }                  //flowspec_all_community_llgr-stale_exact-match
                leaf flowspec_all_community_llgr-stale_exact-match_wide {
                    type enumeration {
                        enum flowspec_all_community_llgr-stale_exact-match_wide;
                    }
                }                  //wide
                leaf flowspec_all_community_llgr-stale_json {
                    type enumeration {
                        enum flowspec_all_community_llgr-stale_json;
                    }
                }                  //flowspec_all_community_llgr-stale_json
                leaf flowspec_all_community_llgr-stale_json_detail {
                    type enumeration {
                        enum flowspec_all_community_llgr-stale_json_detail;
                    }
                }                  //detail
                leaf flowspec_all_community_no-llgr_exact-match {
                    type enumeration {
                        enum flowspec_all_community_no-llgr_exact-match;
                    }
                }                  //flowspec_all_community_no-llgr_exact-match
                leaf flowspec_all_community_no-llgr_exact-match_wide {
                    type enumeration {
                        enum flowspec_all_community_no-llgr_exact-match_wide;
                    }
                }                  //wide
                leaf flowspec_all_community_no-llgr_json {
                    type enumeration {
                        enum flowspec_all_community_no-llgr_json;
                    }
                }                  //flowspec_all_community_no-llgr_json
                leaf flowspec_all_community_no-llgr_json_detail {
                    type enumeration {
                        enum flowspec_all_community_no-llgr_json_detail;
                    }
                }                  //detail
                leaf flowspec_all_community_accept-own_exact-match {
                    type enumeration {
                        enum flowspec_all_community_accept-own_exact-match;
                    }
                }                  //flowspec_all_community_accept-own_exact-match
                leaf flowspec_all_community_accept-own_exact-match_wide {
                    type enumeration {
                        enum flowspec_all_community_accept-own_exact-match_wide;
                    }
                }                  //wide
                leaf flowspec_all_community_accept-own_json {
                    type enumeration {
                        enum flowspec_all_community_accept-own_json;
                    }
                }                  //flowspec_all_community_accept-own_json
                leaf flowspec_all_community_accept-own_json_detail {
                    type enumeration {
                        enum flowspec_all_community_accept-own_json_detail;
                    }
                }                  //detail
                leaf flowspec_all_community_accept-own-nexthop_exact-match {
                    type enumeration {
                        enum flowspec_all_community_accept-own-nexthop_exact-match;
                    }
                }                  //flowspec_all_community_accept-own-nexthop_exact-match
                leaf flowspec_all_community_accept-own-nexthop_exact-match_wide {
                    type enumeration {
                        enum flowspec_all_community_accept-own-nexthop_exact-match_wide;
                    }
                }                  //wide
                leaf flowspec_all_community_accept-own-nexthop_json {
                    type enumeration {
                        enum flowspec_all_community_accept-own-nexthop_json;
                    }
                }                  //flowspec_all_community_accept-own-nexthop_json
                leaf flowspec_all_community_accept-own-nexthop_json_detail {
                    type enumeration {
                        enum flowspec_all_community_accept-own-nexthop_json_detail;
                    }
                }                  //detail
                leaf flowspec_all_community_route-filter-v6_exact-match {
                    type enumeration {
                        enum flowspec_all_community_route-filter-v6_exact-match;
                    }
                }                  //flowspec_all_community_route-filter-v6_exact-match
                leaf flowspec_all_community_route-filter-v6_exact-match_wide {
                    type enumeration {
                        enum flowspec_all_community_route-filter-v6_exact-match_wide;
                    }
                }                  //wide
                leaf flowspec_all_community_route-filter-v6_json {
                    type enumeration {
                        enum flowspec_all_community_route-filter-v6_json;
                    }
                }                  //flowspec_all_community_route-filter-v6_json
                leaf flowspec_all_community_route-filter-v6_json_detail {
                    type enumeration {
                        enum flowspec_all_community_route-filter-v6_json_detail;
                    }
                }                  //detail
                leaf flowspec_all_community_route-filter-v4_exact-match {
                    type enumeration {
                        enum flowspec_all_community_route-filter-v4_exact-match;
                    }
                }                  //flowspec_all_community_route-filter-v4_exact-match
                leaf flowspec_all_community_route-filter-v4_exact-match_wide {
                    type enumeration {
                        enum flowspec_all_community_route-filter-v4_exact-match_wide;
                    }
                }                  //wide
                leaf flowspec_all_community_route-filter-v4_json {
                    type enumeration {
                        enum flowspec_all_community_route-filter-v4_json;
                    }
                }                  //flowspec_all_community_route-filter-v4_json
                leaf flowspec_all_community_route-filter-v4_json_detail {
                    type enumeration {
                        enum flowspec_all_community_route-filter-v4_json_detail;
                    }
                }                  //detail
                leaf flowspec_all_community_route-filter-translated-v6_exact-match {
                    type enumeration {
                        enum flowspec_all_community_route-filter-translated-v6_exact-match;
                    }
                }                  //flowspec_all_community_route-filter-translated-v6_exact-match
                leaf flowspec_all_community_route-filter-translated-v6_exact-match_wide {
                    type enumeration {
                        enum flowspec_all_community_route-filter-translated-v6_exact-match_wide;
                    }
                }                  //wide
                leaf flowspec_all_community_route-filter-translated-v6_json {
                    type enumeration {
                        enum flowspec_all_community_route-filter-translated-v6_json;
                    }
                }                  //flowspec_all_community_route-filter-translated-v6_json
                leaf flowspec_all_community_route-filter-translated-v6_json_detail {
                    type enumeration {
                        enum flowspec_all_community_route-filter-translated-v6_json_detail;
                    }
                }                  //detail
                leaf flowspec_all_community_route-filter-translated-v4_exact-match {
                    type enumeration {
                        enum flowspec_all_community_route-filter-translated-v4_exact-match;
                    }
                }                  //flowspec_all_community_route-filter-translated-v4_exact-match
                leaf flowspec_all_community_route-filter-translated-v4_exact-match_wide {
                    type enumeration {
                        enum flowspec_all_community_route-filter-translated-v4_exact-match_wide;
                    }
                }                  //wide
                leaf flowspec_all_community_route-filter-translated-v4_json {
                    type enumeration {
                        enum flowspec_all_community_route-filter-translated-v4_json;
                    }
                }                  //flowspec_all_community_route-filter-translated-v4_json
                leaf flowspec_all_community_route-filter-translated-v4_json_detail {
                    type enumeration {
                        enum flowspec_all_community_route-filter-translated-v4_json_detail;
                    }
                }                  //detail
                leaf flowspec_all_community_exact-match_json {
                    type enumeration {
                        enum flowspec_all_community_exact-match_json;
                    }
                }                  //flowspec_all_community_exact-match_json
                leaf flowspec_all_community_exact-match_json_detail {
                    type enumeration {
                        enum flowspec_all_community_exact-match_json_detail;
                    }
                }                  //detail
                leaf flowspec_all_summary_established_terse {
                    type enumeration {
                        enum flowspec_all_summary_established_terse;
                    }
                }                  //flowspec_all_summary_established_terse
                leaf flowspec_all_summary_established_terse_json {
                    type enumeration {
                        enum flowspec_all_summary_established_terse_json;
                    }
                }                  //json
                leaf flowspec_all_summary_established_wide {
                    type enumeration {
                        enum flowspec_all_summary_established_wide;
                    }
                }                  //flowspec_all_summary_established_wide
                leaf flowspec_all_summary_established_wide_json {
                    type enumeration {
                        enum flowspec_all_summary_established_wide_json;
                    }
                }                  //json
                leaf flowspec_all_summary_failed_terse {
                    type enumeration {
                        enum flowspec_all_summary_failed_terse;
                    }
                }                  //flowspec_all_summary_failed_terse
                leaf flowspec_all_summary_failed_terse_json {
                    type enumeration {
                        enum flowspec_all_summary_failed_terse_json;
                    }
                }                  //json
                leaf flowspec_all_summary_failed_wide {
                    type enumeration {
                        enum flowspec_all_summary_failed_wide;
                    }
                }                  //flowspec_all_summary_failed_wide
                leaf flowspec_all_summary_failed_wide_json {
                    type enumeration {
                        enum flowspec_all_summary_failed_wide_json;
                    }
                }                  //json
                leaf flowspec_all_summary_terse_wide {
                    type enumeration {
                        enum flowspec_all_summary_terse_wide;
                    }
                }                  //flowspec_all_summary_terse_wide
                leaf flowspec_all_summary_terse_wide_json {
                    type enumeration {
                        enum flowspec_all_summary_terse_wide_json;
                    }
                }                  //json
                leaf flowspec_community_local-AS_exact-match_json {
                    type enumeration {
                        enum flowspec_community_local-AS_exact-match_json;
                    }
                }                  //flowspec_community_local-AS_exact-match_json
                leaf flowspec_community_local-AS_exact-match_json_detail {
                    type enumeration {
                        enum flowspec_community_local-AS_exact-match_json_detail;
                    }
                }                  //detail
                leaf flowspec_community_no-advertise_exact-match_json {
                    type enumeration {
                        enum flowspec_community_no-advertise_exact-match_json;
                    }
                }                  //flowspec_community_no-advertise_exact-match_json
                leaf flowspec_community_no-advertise_exact-match_json_detail {
                    type enumeration {
                        enum flowspec_community_no-advertise_exact-match_json_detail;
                    }
                }                  //detail
                leaf flowspec_community_no-export_exact-match_json {
                    type enumeration {
                        enum flowspec_community_no-export_exact-match_json;
                    }
                }                  //flowspec_community_no-export_exact-match_json
                leaf flowspec_community_no-export_exact-match_json_detail {
                    type enumeration {
                        enum flowspec_community_no-export_exact-match_json_detail;
                    }
                }                  //detail
                leaf flowspec_community_graceful-shutdown_exact-match_json {
                    type enumeration {
                        enum flowspec_community_graceful-shutdown_exact-match_json;
                    }
                }                  //flowspec_community_graceful-shutdown_exact-match_json
                leaf flowspec_community_graceful-shutdown_exact-match_json_detail {
                    type enumeration {
                        enum flowspec_community_graceful-shutdown_exact-match_json_detail;
                    }
                }                  //detail
                leaf flowspec_community_no-peer_exact-match_json {
                    type enumeration {
                        enum flowspec_community_no-peer_exact-match_json;
                    }
                }                  //flowspec_community_no-peer_exact-match_json
                leaf flowspec_community_no-peer_exact-match_json_detail {
                    type enumeration {
                        enum flowspec_community_no-peer_exact-match_json_detail;
                    }
                }                  //detail
                leaf flowspec_community_blackhole_exact-match_json {
                    type enumeration {
                        enum flowspec_community_blackhole_exact-match_json;
                    }
                }                  //flowspec_community_blackhole_exact-match_json
                leaf flowspec_community_blackhole_exact-match_json_detail {
                    type enumeration {
                        enum flowspec_community_blackhole_exact-match_json_detail;
                    }
                }                  //detail
                leaf flowspec_community_llgr-stale_exact-match_json {
                    type enumeration {
                        enum flowspec_community_llgr-stale_exact-match_json;
                    }
                }                  //flowspec_community_llgr-stale_exact-match_json
                leaf flowspec_community_llgr-stale_exact-match_json_detail {
                    type enumeration {
                        enum flowspec_community_llgr-stale_exact-match_json_detail;
                    }
                }                  //detail
                leaf flowspec_community_no-llgr_exact-match_json {
                    type enumeration {
                        enum flowspec_community_no-llgr_exact-match_json;
                    }
                }                  //flowspec_community_no-llgr_exact-match_json
                leaf flowspec_community_no-llgr_exact-match_json_detail {
                    type enumeration {
                        enum flowspec_community_no-llgr_exact-match_json_detail;
                    }
                }                  //detail
                leaf flowspec_community_accept-own_exact-match_json {
                    type enumeration {
                        enum flowspec_community_accept-own_exact-match_json;
                    }
                }                  //flowspec_community_accept-own_exact-match_json
                leaf flowspec_community_accept-own_exact-match_json_detail {
                    type enumeration {
                        enum flowspec_community_accept-own_exact-match_json_detail;
                    }
                }                  //detail
                leaf flowspec_community_accept-own-nexthop_exact-match_json {
                    type enumeration {
                        enum flowspec_community_accept-own-nexthop_exact-match_json;
                    }
                }                  //flowspec_community_accept-own-nexthop_exact-match_json
                leaf flowspec_community_accept-own-nexthop_exact-match_json_detail {
                    type enumeration {
                        enum flowspec_community_accept-own-nexthop_exact-match_json_detail;
                    }
                }                  //detail
                leaf flowspec_community_route-filter-v6_exact-match_json {
                    type enumeration {
                        enum flowspec_community_route-filter-v6_exact-match_json;
                    }
                }                  //flowspec_community_route-filter-v6_exact-match_json
                leaf flowspec_community_route-filter-v6_exact-match_json_detail {
                    type enumeration {
                        enum flowspec_community_route-filter-v6_exact-match_json_detail;
                    }
                }                  //detail
                leaf flowspec_community_route-filter-v4_exact-match_json {
                    type enumeration {
                        enum flowspec_community_route-filter-v4_exact-match_json;
                    }
                }                  //flowspec_community_route-filter-v4_exact-match_json
                leaf flowspec_community_route-filter-v4_exact-match_json_detail {
                    type enumeration {
                        enum flowspec_community_route-filter-v4_exact-match_json_detail;
                    }
                }                  //detail
                leaf flowspec_community_route-filter-translated-v6_exact-match_json {
                    type enumeration {
                        enum flowspec_community_route-filter-translated-v6_exact-match_json;
                    }
                }                  //flowspec_community_route-filter-translated-v6_exact-match_json
                leaf flowspec_community_route-filter-translated-v6_exact-match_json_detail {
                    type enumeration {
                        enum flowspec_community_route-filter-translated-v6_exact-match_json_detail;
                    }
                }                  //detail
                leaf flowspec_community_route-filter-translated-v4_exact-match_json {
                    type enumeration {
                        enum flowspec_community_route-filter-translated-v4_exact-match_json;
                    }
                }                  //flowspec_community_route-filter-translated-v4_exact-match_json
                leaf flowspec_community_route-filter-translated-v4_exact-match_json_detail {
                    type enumeration {
                        enum flowspec_community_route-filter-translated-v4_exact-match_json_detail;
                    }
                }                  //detail
                leaf flowspec_summary_established_terse_wide {
                    type enumeration {
                        enum flowspec_summary_established_terse_wide;
                    }
                }                  //flowspec_summary_established_terse_wide
                leaf flowspec_summary_established_terse_wide_json {
                    type enumeration {
                        enum flowspec_summary_established_terse_wide_json;
                    }
                }                  //json
                leaf flowspec_summary_failed_terse_wide {
                    type enumeration {
                        enum flowspec_summary_failed_terse_wide;
                    }
                }                  //flowspec_summary_failed_terse_wide
                leaf flowspec_summary_failed_terse_wide_json {
                    type enumeration {
                        enum flowspec_summary_failed_terse_wide_json;
                    }
                }                  //json
                leaf unicast_all_community_local-AS_exact-match_json {
                    type enumeration {
                        enum unicast_all_community_local-AS_exact-match_json;
                    }
                }                  //unicast_all_community_local-AS_exact-match_json
                leaf unicast_all_community_local-AS_exact-match_json_detail {
                    type enumeration {
                        enum unicast_all_community_local-AS_exact-match_json_detail;
                    }
                }                  //detail
                leaf unicast_all_community_no-advertise_exact-match_json {
                    type enumeration {
                        enum unicast_all_community_no-advertise_exact-match_json;
                    }
                }                  //unicast_all_community_no-advertise_exact-match_json
                leaf unicast_all_community_no-advertise_exact-match_json_detail {
                    type enumeration {
                        enum unicast_all_community_no-advertise_exact-match_json_detail;
                    }
                }                  //detail
                leaf unicast_all_community_no-export_exact-match_json {
                    type enumeration {
                        enum unicast_all_community_no-export_exact-match_json;
                    }
                }                  //unicast_all_community_no-export_exact-match_json
                leaf unicast_all_community_no-export_exact-match_json_detail {
                    type enumeration {
                        enum unicast_all_community_no-export_exact-match_json_detail;
                    }
                }                  //detail
                leaf unicast_all_community_graceful-shutdown_exact-match_json {
                    type enumeration {
                        enum unicast_all_community_graceful-shutdown_exact-match_json;
                    }
                }                  //unicast_all_community_graceful-shutdown_exact-match_json
                leaf unicast_all_community_graceful-shutdown_exact-match_json_detail {
                    type enumeration {
                        enum unicast_all_community_graceful-shutdown_exact-match_json_detail;
                    }
                }                  //detail
                leaf unicast_all_community_no-peer_exact-match_json {
                    type enumeration {
                        enum unicast_all_community_no-peer_exact-match_json;
                    }
                }                  //unicast_all_community_no-peer_exact-match_json
                leaf unicast_all_community_no-peer_exact-match_json_detail {
                    type enumeration {
                        enum unicast_all_community_no-peer_exact-match_json_detail;
                    }
                }                  //detail
                leaf unicast_all_community_blackhole_exact-match_json {
                    type enumeration {
                        enum unicast_all_community_blackhole_exact-match_json;
                    }
                }                  //unicast_all_community_blackhole_exact-match_json
                leaf unicast_all_community_blackhole_exact-match_json_detail {
                    type enumeration {
                        enum unicast_all_community_blackhole_exact-match_json_detail;
                    }
                }                  //detail
                leaf unicast_all_community_llgr-stale_exact-match_json {
                    type enumeration {
                        enum unicast_all_community_llgr-stale_exact-match_json;
                    }
                }                  //unicast_all_community_llgr-stale_exact-match_json
                leaf unicast_all_community_llgr-stale_exact-match_json_detail {
                    type enumeration {
                        enum unicast_all_community_llgr-stale_exact-match_json_detail;
                    }
                }                  //detail
                leaf unicast_all_community_no-llgr_exact-match_json {
                    type enumeration {
                        enum unicast_all_community_no-llgr_exact-match_json;
                    }
                }                  //unicast_all_community_no-llgr_exact-match_json
                leaf unicast_all_community_no-llgr_exact-match_json_detail {
                    type enumeration {
                        enum unicast_all_community_no-llgr_exact-match_json_detail;
                    }
                }                  //detail
                leaf unicast_all_community_accept-own_exact-match_json {
                    type enumeration {
                        enum unicast_all_community_accept-own_exact-match_json;
                    }
                }                  //unicast_all_community_accept-own_exact-match_json
                leaf unicast_all_community_accept-own_exact-match_json_detail {
                    type enumeration {
                        enum unicast_all_community_accept-own_exact-match_json_detail;
                    }
                }                  //detail
                leaf unicast_all_community_accept-own-nexthop_exact-match_json {
                    type enumeration {
                        enum unicast_all_community_accept-own-nexthop_exact-match_json;
                    }
                }                  //unicast_all_community_accept-own-nexthop_exact-match_json
                leaf unicast_all_community_accept-own-nexthop_exact-match_json_detail {
                    type enumeration {
                        enum unicast_all_community_accept-own-nexthop_exact-match_json_detail;
                    }
                }                  //detail
                leaf unicast_all_community_route-filter-v6_exact-match_json {
                    type enumeration {
                        enum unicast_all_community_route-filter-v6_exact-match_json;
                    }
                }                  //unicast_all_community_route-filter-v6_exact-match_json
                leaf unicast_all_community_route-filter-v6_exact-match_json_detail {
                    type enumeration {
                        enum unicast_all_community_route-filter-v6_exact-match_json_detail;
                    }
                }                  //detail
                leaf unicast_all_community_route-filter-v4_exact-match_json {
                    type enumeration {
                        enum unicast_all_community_route-filter-v4_exact-match_json;
                    }
                }                  //unicast_all_community_route-filter-v4_exact-match_json
                leaf unicast_all_community_route-filter-v4_exact-match_json_detail {
                    type enumeration {
                        enum unicast_all_community_route-filter-v4_exact-match_json_detail;
                    }
                }                  //detail
                leaf unicast_all_community_route-filter-translated-v6_exact-match_json {
                    type enumeration {
                        enum unicast_all_community_route-filter-translated-v6_exact-match_json;
                    }
                }                  //unicast_all_community_route-filter-translated-v6_exact-match_json
                leaf unicast_all_community_route-filter-translated-v6_exact-match_json_detail {
                    type enumeration {
                        enum unicast_all_community_route-filter-translated-v6_exact-match_json_detail;
                    }
                }                  //detail
                leaf unicast_all_community_route-filter-translated-v4_exact-match_json {
                    type enumeration {
                        enum unicast_all_community_route-filter-translated-v4_exact-match_json;
                    }
                }                  //unicast_all_community_route-filter-translated-v4_exact-match_json
                leaf unicast_all_community_route-filter-translated-v4_exact-match_json_detail {
                    type enumeration {
                        enum unicast_all_community_route-filter-translated-v4_exact-match_json_detail;
                    }
                }                  //detail
                leaf unicast_all_summary_established_terse_wide {
                    type enumeration {
                        enum unicast_all_summary_established_terse_wide;
                    }
                }                  //unicast_all_summary_established_terse_wide
                leaf unicast_all_summary_established_terse_wide_json {
                    type enumeration {
                        enum unicast_all_summary_established_terse_wide_json;
                    }
                }                  //json
                leaf unicast_all_summary_failed_terse_wide {
                    type enumeration {
                        enum unicast_all_summary_failed_terse_wide;
                    }
                }                  //unicast_all_summary_failed_terse_wide
                leaf unicast_all_summary_failed_terse_wide_json {
                    type enumeration {
                        enum unicast_all_summary_failed_terse_wide_json;
                    }
                }                  //json
                leaf flowspec_all_community_local-AS_exact-match_json {
                    type enumeration {
                        enum flowspec_all_community_local-AS_exact-match_json;
                    }
                }                  //flowspec_all_community_local-AS_exact-match_json
                leaf flowspec_all_community_local-AS_exact-match_json_detail {
                    type enumeration {
                        enum flowspec_all_community_local-AS_exact-match_json_detail;
                    }
                }                  //detail
                leaf flowspec_all_community_no-advertise_exact-match_json {
                    type enumeration {
                        enum flowspec_all_community_no-advertise_exact-match_json;
                    }
                }                  //flowspec_all_community_no-advertise_exact-match_json
                leaf flowspec_all_community_no-advertise_exact-match_json_detail {
                    type enumeration {
                        enum flowspec_all_community_no-advertise_exact-match_json_detail;
                    }
                }                  //detail
                leaf flowspec_all_community_no-export_exact-match_json {
                    type enumeration {
                        enum flowspec_all_community_no-export_exact-match_json;
                    }
                }                  //flowspec_all_community_no-export_exact-match_json
                leaf flowspec_all_community_no-export_exact-match_json_detail {
                    type enumeration {
                        enum flowspec_all_community_no-export_exact-match_json_detail;
                    }
                }                  //detail
                leaf flowspec_all_community_graceful-shutdown_exact-match_json {
                    type enumeration {
                        enum flowspec_all_community_graceful-shutdown_exact-match_json;
                    }
                }                  //flowspec_all_community_graceful-shutdown_exact-match_json
                leaf flowspec_all_community_graceful-shutdown_exact-match_json_detail {
                    type enumeration {
                        enum flowspec_all_community_graceful-shutdown_exact-match_json_detail;
                    }
                }                  //detail
                leaf flowspec_all_community_no-peer_exact-match_json {
                    type enumeration {
                        enum flowspec_all_community_no-peer_exact-match_json;
                    }
                }                  //flowspec_all_community_no-peer_exact-match_json
                leaf flowspec_all_community_no-peer_exact-match_json_detail {
                    type enumeration {
                        enum flowspec_all_community_no-peer_exact-match_json_detail;
                    }
                }                  //detail
                leaf flowspec_all_community_blackhole_exact-match_json {
                    type enumeration {
                        enum flowspec_all_community_blackhole_exact-match_json;
                    }
                }                  //flowspec_all_community_blackhole_exact-match_json
                leaf flowspec_all_community_blackhole_exact-match_json_detail {
                    type enumeration {
                        enum flowspec_all_community_blackhole_exact-match_json_detail;
                    }
                }                  //detail
                leaf flowspec_all_community_llgr-stale_exact-match_json {
                    type enumeration {
                        enum flowspec_all_community_llgr-stale_exact-match_json;
                    }
                }                  //flowspec_all_community_llgr-stale_exact-match_json
                leaf flowspec_all_community_llgr-stale_exact-match_json_detail {
                    type enumeration {
                        enum flowspec_all_community_llgr-stale_exact-match_json_detail;
                    }
                }                  //detail
                leaf flowspec_all_community_no-llgr_exact-match_json {
                    type enumeration {
                        enum flowspec_all_community_no-llgr_exact-match_json;
                    }
                }                  //flowspec_all_community_no-llgr_exact-match_json
                leaf flowspec_all_community_no-llgr_exact-match_json_detail {
                    type enumeration {
                        enum flowspec_all_community_no-llgr_exact-match_json_detail;
                    }
                }                  //detail
                leaf flowspec_all_community_accept-own_exact-match_json {
                    type enumeration {
                        enum flowspec_all_community_accept-own_exact-match_json;
                    }
                }                  //flowspec_all_community_accept-own_exact-match_json
                leaf flowspec_all_community_accept-own_exact-match_json_detail {
                    type enumeration {
                        enum flowspec_all_community_accept-own_exact-match_json_detail;
                    }
                }                  //detail
                leaf flowspec_all_community_accept-own-nexthop_exact-match_json {
                    type enumeration {
                        enum flowspec_all_community_accept-own-nexthop_exact-match_json;
                    }
                }                  //flowspec_all_community_accept-own-nexthop_exact-match_json
                leaf flowspec_all_community_accept-own-nexthop_exact-match_json_detail {
                    type enumeration {
                        enum flowspec_all_community_accept-own-nexthop_exact-match_json_detail;
                    }
                }                  //detail
                leaf flowspec_all_community_route-filter-v6_exact-match_json {
                    type enumeration {
                        enum flowspec_all_community_route-filter-v6_exact-match_json;
                    }
                }                  //flowspec_all_community_route-filter-v6_exact-match_json
                leaf flowspec_all_community_route-filter-v6_exact-match_json_detail {
                    type enumeration {
                        enum flowspec_all_community_route-filter-v6_exact-match_json_detail;
                    }
                }                  //detail
                leaf flowspec_all_community_route-filter-v4_exact-match_json {
                    type enumeration {
                        enum flowspec_all_community_route-filter-v4_exact-match_json;
                    }
                }                  //flowspec_all_community_route-filter-v4_exact-match_json
                leaf flowspec_all_community_route-filter-v4_exact-match_json_detail {
                    type enumeration {
                        enum flowspec_all_community_route-filter-v4_exact-match_json_detail;
                    }
                }                  //detail
                leaf flowspec_all_community_route-filter-translated-v6_exact-match_json {
                    type enumeration {
                        enum flowspec_all_community_route-filter-translated-v6_exact-match_json;
                    }
                }                  //flowspec_all_community_route-filter-translated-v6_exact-match_json
                leaf flowspec_all_community_route-filter-translated-v6_exact-match_json_detail {
                    type enumeration {
                        enum flowspec_all_community_route-filter-translated-v6_exact-match_json_detail;
                    }
                }                  //detail
                leaf flowspec_all_community_route-filter-translated-v4_exact-match_json {
                    type enumeration {
                        enum flowspec_all_community_route-filter-translated-v4_exact-match_json;
                    }
                }                  //flowspec_all_community_route-filter-translated-v4_exact-match_json
                leaf flowspec_all_community_route-filter-translated-v4_exact-match_json_detail {
                    type enumeration {
                        enum flowspec_all_community_route-filter-translated-v4_exact-match_json_detail;
                    }
                }                  //detail
                leaf flowspec_all_summary_established_terse_wide {
                    type enumeration {
                        enum flowspec_all_summary_established_terse_wide;
                    }
                }                  //flowspec_all_summary_established_terse_wide
                leaf flowspec_all_summary_established_terse_wide_json {
                    type enumeration {
                        enum flowspec_all_summary_established_terse_wide_json;
                    }
                }                  //json
                leaf flowspec_all_summary_failed_terse_wide {
                    type enumeration {
                        enum flowspec_all_summary_failed_terse_wide;
                    }
                }                  //flowspec_all_summary_failed_terse_wide
                leaf flowspec_all_summary_failed_terse_wide_json {
                    type enumeration {
                        enum flowspec_all_summary_failed_terse_wide_json;
                    }
                }                  //json
                leaf peer-group {
                    type enumeration {
                        enum peer-group;
                    }
                }                  //peer-group
                leaf peer-group_json {
                    type enumeration {
                        enum peer-group_json;
                    }
                }                  //json
                leaf statistics-all {
                    type enumeration {
                        enum statistics-all;
                    }
                }                  //statistics-all
                leaf statistics-all_json {
                    type enumeration {
                        enum statistics-all_json;
                    }
                }                  //json
                leaf martian_next-hop {
                    type enumeration {
                        enum martian_next-hop;
                    }
                }                  //next-hop
                leaf l2vpn_evpn_statistics {
                    type enumeration {
                        enum l2vpn_evpn_statistics;
                    }
                }                  //l2vpn_evpn_statistics
                leaf l2vpn_evpn_statistics_json {
                    type enumeration {
                        enum l2vpn_evpn_statistics_json;
                    }
                }                  //json
            }
            container show_bgp_as-path-access-list {
                leaf AS_PATH_ACCESS_LIST {
                    type string;
                }                  //AS_PATH_FILTER_NAME
                leaf json {
                    type enumeration {
                        enum json;
                    }
                }                  //json
            }
            container show_bgp_extcommunity-list {
                leaf EXTCOMMUNITY-LIST_NUMBER {
                    type union {
                        type int32;
                        type string;
                    }
                }                  //<(1-500)|EXTCOMMUNITY_LIST_NAME>
                leaf detail {
                    type enumeration {
                        enum detail;
                    }
                }                  //detail
            }
            container show_bgp_mac {
                leaf hash {
                    type enumeration {
                        enum hash;
                    }
                }                  //hash
            }
            container show_bgp_segment-routing {
                leaf srv6 {
                    type enumeration {
                        enum srv6;
                    }
                }                  //srv6
            }
            container show_bgp_vni {
                leaf VNI_NUMBER {
                    type int32;
                }                  //(1-16777215)
                leaf vtep {
                    type enumeration {
                        enum vtep;
                    }
                }                  //vtep
                leaf REMOTE_VTEP_IP_ADDRESS {
                    type inet:ipv4-address;
                }                  //A.B.C.D
                leaf json {
                    type enumeration {
                        enum json;
                    }
                }                  //json
                leaf type {
                    type enumeration {
                        enum type;
                    }
                }                  //type
                leaf EAD_TYPE {
                    type enumeration {
                        enum 1;
                        enum ead;
                    }
                }                  //<1|ead> ['EAD (Type-1) route', 'EAD (Type-1) route']
                leaf MACIP_TYPE {
                    type enumeration {
                        enum 2;
                        enum macip;
                    }
                }                  //<2|macip> ['MAC-IP (Type-2) route', 'MAC-IP (Type-2) route']
                leaf ip {
                    type enumeration {
                        enum ip;
                    }
                }                  //ip
                leaf IP_ADDRESS {
                    type union {
                        type inet:ipv4-address;
                        type inet:ipv6-address;
                    }
                }                  //<A.B.C.D|X:X::X:X>
                leaf ip_vtep {
                    type enumeration {
                        enum ip_vtep;
                    }
                }                  //vtep
                leaf ip_json {
                    type enumeration {
                        enum ip_json;
                    }
                }                  //json
                leaf mac {
                    type enumeration {
                        enum mac;
                    }
                }                  //mac
                leaf mac_vtep {
                    type enumeration {
                        enum mac_vtep;
                    }
                }                  //vtep
                leaf mac_json {
                    type enumeration {
                        enum mac_json;
                    }
                }                  //json
                leaf MULTICAST_TYPE {
                    type enumeration {
                        enum 3;
                        enum multicast;
                    }
                }                  //<3|multicast> ['Multicast (Type-3) route', 'Multicast (Type-3) route']
            }
            container show_babel_interface {
                leaf INTERFACE {
                    type string;
                }                  //IFNAME
            }
            container show_babel_neighbor {
                leaf INTERFACE {
                    type string;
                }                  //IFNAME
            }
            container show_babel_route {
                leaf IPV4_PREFIX {
                    type union {
                        type inet:ipv4-prefix;
                        type inet:ipv6-prefix;
                    }
                }                  //<A.B.C.D/M|X:X::X:X/M>
                leaf IPV4_ADDRESS {
                    type inet:ipv4-address;
                }                  //A.B.C.D
                leaf IPV6_ADDRESS {
                    type inet:ipv6-address;
                }                  //X:X::X:X
            }
            container show_configuration_candidate {
                leaf OUTPUT_FORMAT {
                    type enumeration {
                        enum json;
                        enum xml;
                    }
                }                  //<json|xml> ['Change output format to JSON', 'Change output format to XML']
                leaf translate {
                    type enumeration {
                        enum translate;
                    }
                }                  //translate
                leaf YANG_MODULE_TRANSLATOR {
                    type string;
                }                  //WORD
                leaf CHOICE_CASE {
                    type enumeration {
                        enum with-defaults;
                        enum changes;
                    }
                }                  //<with-defaults|changes> ['Show default values', 'Show changes applied in the candidate configuration']
            }
            container show_configuration_running {
                leaf OUTPUT_FORMAT {
                    type enumeration {
                        enum json;
                        enum xml;
                    }
                }                  //<json|xml> ['Change output format to JSON', 'Change output format to XML']
                leaf translate {
                    type enumeration {
                        enum translate;
                    }
                }                  //translate
                leaf YANG_MODULE_TRANSLATOR {
                    type string;
                }                  //WORD
                leaf with-defaults {
                    type enumeration {
                        enum with-defaults;
                    }
                }                  //with-defaults
                leaf DAEMONS_LIST {
                    type enumeration {
                        enum babeld;
                        enum bgpd;
                        enum fabricd;
                        enum ldpd;
                        enum ospfd;
                        enum pbrd;
                        enum pimd;
                        enum ripngd;
                        enum vrrpd;
                        enum bfdd;
                        enum eigrpd;
                        enum isisd;
                        enum nhrpd;
                        enum ospf6d;
                        enum pathd;
                        enum pim6d;
                        enum ripd;
                        enum staticd;
                        enum zebra;
                    }
                }                  //<babeld|bgpd|fabricd|ldpd|ospfd|pbrd|pimd|ripngd|vrrpd|bfdd|eigrpd|isisd|nhrpd|ospf6d|pathd|pim6d|ripd|staticd|zebra> ['For the babeld daemon', 'For the bgpd daemon', 'For the fabricd daemon', 'For the ldpd daemon', 'For the ospfd daemon', 'For the pbrd daemon', 'For the pimd daemon', 'For the ripngd daemon', 'For the vrrpd daemon', 'For the bfdd daemon', 'For the eigrpd daemon', 'For the isisd daemon', 'For the nhrpd daemon', 'For the ospf6d daemon', 'For the pathd daemon', 'For the pim6d daemom', 'For the ripd daemon', 'For the staticd daemon', 'For the zebra daemon']
            }
            container show_configuration_transaction {
                leaf TRANSACTION_ID {
                    type int32;
                }                  //(1-4294967295)
                leaf OUTPUT_FORMAT {
                    type enumeration {
                        enum json;
                        enum xml;
                    }
                }                  //<json|xml> ['Change output format to JSON', 'Change output format to XML']
                leaf translate {
                    type enumeration {
                        enum translate;
                    }
                }                  //translate
                leaf YANG_MODULE_TRANSLATOR {
                    type string;
                }                  //WORD
                leaf CHOICE_CASE {
                    type enumeration {
                        enum with-defaults;
                        enum changes;
                    }
                }                  //<with-defaults|changes> ['Show default values', 'Show changes compared to the previous transaction']
            }
            container show_evpn_access-vlan {
                leaf VLAN_ID {
                    type int32;
                }                  //(1-4094)
                leaf json {
                    type enumeration {
                        enum json;
                    }
                }                  //json
            }
            container show_evpn_es {
                leaf ES_ID {
                    type string;
                }                  //NAME
                leaf json {
                    type enumeration {
                        enum json;
                    }
                }                  //json
            }
            container show_evpn_es-evi {
                leaf vni {
                    type enumeration {
                        enum vni;
                    }
                }                  //vni
                leaf VNI {
                    type int32;
                }                  //(1-16777215)
                leaf detail {
                    type enumeration {
                        enum detail;
                    }
                }                  //detail
                leaf detail_json {
                    type enumeration {
                        enum detail_json;
                    }
                }                  //json
                leaf json {
                    type enumeration {
                        enum json;
                    }
                }                  //json
            }
            container show_evpn_l2-nh {
                leaf json {
                    type enumeration {
                        enum json;
                    }
                }                  //json
            }
            container show_evpn_vni {
                leaf VNI_NUMBER {
                    type int32;
                }                  //(1-16777215)
                leaf json {
                    type enumeration {
                        enum json;
                    }
                }                  //json
            }
            container show_interface_vrf {
                leaf THE_VRF_NAME {
                    type string;
                }                  //NAME
                leaf brief {
                    type enumeration {
                        enum brief;
                    }
                }                  //brief
                leaf brief_json {
                    type enumeration {
                        enum brief_json;
                    }
                }                  //json
                leaf json {
                    type enumeration {
                        enum json;
                    }
                }                  //json
            }
            container show_interface_brief {
                leaf json {
                    type enumeration {
                        enum json;
                    }
                }                  //json
            }
            container show_isis_database {
                leaf LSP_ID {
                    type string;
                }                  //WORD
                leaf json {
                    type enumeration {
                        enum json;
                    }
                }                  //json
            }
            container show_isis_fast-reroute {
                leaf summary {
                    type enumeration {
                        enum summary;
                    }
                }                  //summary
            }
            container show_isis_interface {
                leaf IS-IS_INTERFACE_NAME {
                    type string;
                }                  //WORD
                leaf json {
                    type enumeration {
                        enum json;
                    }
                }                  //json
            }
            container show_isis_mpls-te {
                leaf router {
                    type enumeration {
                        enum router;
                    }
                }                  //router
            }
            container show_isis_neighbor {
                leaf SYSTEM_ID {
                    type string;
                }                  //WORD
                leaf json {
                    type enumeration {
                        enum json;
                    }
                }                  //json
            }
            container show_isis_summary {
                leaf json {
                    type enumeration {
                        enum json;
                    }
                }                  //json
            }
            container show_isis_segment-routing {
                leaf node {
                    type enumeration {
                        enum node;
                    }
                }                  //node
            }
            container show_mpls_fec {
                leaf IPV4_PREFIX {
                    type union {
                        type inet:ipv4-prefix;
                        type inet:ipv6-prefix;
                    }
                }                  //<A.B.C.D/M|X:X::X:X/M>
            }
            container show_mpls_table {
                leaf LSP_TO_DISPLAY_INFORMATION {
                    type int32;
                }                  //(16-1048575)
                leaf json {
                    type enumeration {
                        enum json;
                    }
                }                  //json
            }
            container show_pathd_ted {
                leaf database {
                    type enumeration {
                        enum database;
                    }
                }                  //database
                leaf CHOICE_CASE {
                    type enumeration {
                        enum verbose;
                        enum json;
                    }
                }                  //<verbose|json> ['verbose output', 'Show complete received TED database']
            }
            container show_pbr_interface {
                leaf PBR_INTERFACE_NAME {
                    type string;
                }                  //NAME
                leaf json {
                    type enumeration {
                        enum json;
                    }
                }                  //json
            }
            container show_pbr_ipset {
                leaf IPSET_NAME_INFORMATION {
                    type string;
                }                  //WORD
            }
            container show_pbr_iptable {
                leaf IPTABLE_NAME_INFORMATION {
                    type string;
                }                  //WORD
            }
            container show_pbr_map {
                leaf PBR_MAP_NAME {
                    type string;
                }                  //NAME
                leaf detail {
                    type enumeration {
                        enum detail;
                    }
                }                  //detail
                leaf json {
                    type enumeration {
                        enum json;
                    }
                }                  //json
            }
            container show_pbr_nexthop-groups {
                leaf OPTIONAL_NAME_OF_THE {
                    type string;
                }                  //WORD
                leaf json {
                    type enumeration {
                        enum json;
                    }
                }                  //json
            }
            container show_rpki_cache-connection {
                leaf json {
                    type enumeration {
                        enum json;
                    }
                }                  //json
            }
            container show_rpki_cache-server {
                leaf json {
                    type enumeration {
                        enum json;
                    }
                }                  //json
            }
            container show_rpki_prefix-table {
                leaf json {
                    type enumeration {
                        enum json;
                    }
                }                  //json
            }
            container show_thread_cpu {
                leaf DISPLAY_FILTER {
                    type string;
                }                  //FILTER
            }
            container show_vnc_nves {
                leaf OVERLAY_ADDRESS_MODE {
                    type enumeration {
                        enum vn;
                        enum un;
                    }
                }                  //<vn|un> ['VN address of NVE', 'UN address of NVE']
                leaf IP_ADDRESS {
                    type union {
                        type inet:ipv4-address;
                        type inet:ipv6-address;
                    }
                }                  //<A.B.C.D|X:X::X:X>
            }
            container show_vnc_queries {
                leaf IPV4_PREFIX {
                    type union {
                        type inet:ipv4-address;
                        type inet:ipv4-prefix;
                        type inet:ipv6-address;
                        type inet:ipv6-prefix;
                        type string;
                    }
                }                  //<A.B.C.D|A.B.C.D/M|X:X::X:X|X:X::X:X/M|X:X:X:X:X:X>
            }
            container show_vnc_registrations {
                leaf REGISTRATION_FILTER {
                    type enumeration {
                        enum all;
                        enum holddown;
                        enum imported;
                        enum local;
                        enum remote;
                    }
                }                  //<all|holddown|imported|local|remote> ['show all registrations', 'show only registrations in holddown', 'show only imported prefixes', 'show only local registrations', 'show only remote registrations']
                leaf IPV4_PREFIX {
                    type union {
                        type inet:ipv4-address;
                        type inet:ipv4-prefix;
                        type inet:ipv6-address;
                        type inet:ipv6-prefix;
                        type string;
                    }
                }                  //<A.B.C.D|A.B.C.D/M|X:X::X:X|X:X::X:X/M|X:X:X:X:X:X>
            }
            container show_vnc_responses {
                leaf QUERY_STATUS {
                    type enumeration {
                        enum active;
                        enum removed;
                    }
                }                  //<active|removed> ['show only active query responses', 'show only removed query responses']
                leaf IPV4_PREFIX {
                    type union {
                        type inet:ipv4-address;
                        type inet:ipv4-prefix;
                        type inet:ipv6-address;
                        type inet:ipv6-prefix;
                        type string;
                    }
                }                  //<A.B.C.D|A.B.C.D/M|X:X::X:X|X:X::X:X/M|X:X:X:X:X:X>
            }
            container show_vrf_vni {
                leaf json {
                    type enumeration {
                        enum json;
                    }
                }                  //json
            }
            container show_zebra_dplane {
                leaf detailed {
                    type enumeration {
                        enum detailed;
                    }
                }                  //detailed
            }
            container show_zebra_client {
                leaf summary {
                    type enumeration {
                        enum summary;
                    }
                }                  //summary
            }
            container show_zebra_fpm {
                leaf stats {
                    type enumeration {
                        enum stats;
                    }
                }                  //stats
            }
            container show_bfd_peers {
                leaf json {
                    type enumeration {
                        enum json;
                    }
                }                  //json
            }
            container show_bfd_peer {
                leaf PEER_LABEL {
                    type string;
                }                  //WORD
                leaf json {
                    type enumeration {
                        enum json;
                    }
                }                  //json
                leaf counters {
                    type enumeration {
                        enum counters;
                    }
                }                  //counters
                leaf counters_json {
                    type enumeration {
                        enum counters_json;
                    }
                }                  //json
                leaf IP_ADDRESS {
                    type union {
                        type inet:ipv4-address;
                        type inet:ipv6-address;
                    }
                }                  //<A.B.C.D|X:X::X:X>
                leaf multihop {
                    type enumeration {
                        enum multihop;
                    }
                }                  //multihop
                leaf multihop_json {
                    type enumeration {
                        enum multihop_json;
                    }
                }                  //json
                leaf local-address {
                    type enumeration {
                        enum local-address;
                    }
                }                  //local-address
                leaf interface {
                    type enumeration {
                        enum interface;
                    }
                }                  //interface
                leaf CONFIGURE_LOCAL_INTERFACE_NAME {
                    type string;
                }                  //IFNAME
                leaf multihop_counters {
                    type enumeration {
                        enum multihop_counters;
                    }
                }                  //multihop_counters
                leaf multihop_counters_json {
                    type enumeration {
                        enum multihop_counters_json;
                    }
                }                  //json
            }
            container show_debugging_hashtable {
                leaf statistics {
                    type enumeration {
                        enum statistics;
                    }
                }                  //statistics
            }
            container show_fpm_counters {
                leaf json {
                    type enumeration {
                        enum json;
                    }
                }                  //json
            }
            container show_mac_access-list {
                leaf MAC_ADDRESS {
                    type string;
                }                  //ACCESSLIST_MAC_NAME
            }
            container show_openfabric_flooding {
                leaf LSP_ID {
                    type string;
                }                  //WORD
            }
            container show_sharp_cspf {
                leaf source {
                    type enumeration {
                        enum source;
                    }
                }                  //source
                leaf IP_ADDRESS {
                    type union {
                        type inet:ipv4-address;
                        type inet:ipv6-address;
                    }
                }                  //<A.B.C.D|X:X::X:X>
                leaf destination {
                    type enumeration {
                        enum destination;
                    }
                }                  //destination
                leaf CHOICE_CASE {
                    type enumeration {
                        enum metric;
                        enum te-metric;
                        enum delay;
                    }
                }                  //<metric|te-metric|delay> ['Maximum Metric', 'Maximum TE Metric', 'Maxim Delay']
                leaf VALUE_OF_MAXIMUM_COST {
                    type int32;
                }                  //(0-16777215)
                leaf rsv-bw {
                    type enumeration {
                        enum rsv-bw;
                    }
                }                  //rsv-bw
                leaf CLASS_OF_SERVICE_OR {
                    type int32;
                }                  //(0-7)
                leaf BYTESSECOND {
                    type string;
                }                  //BANDWIDTH
            }
            container show_sharp_ted {
                leaf verbose {
                    type enumeration {
                        enum verbose;
                    }
                }                  //verbose
                leaf json {
                    type enumeration {
                        enum json;
                    }
                }                  //json
            }
            container show_yang_module {
                leaf module-translator {
                    type enumeration {
                        enum module-translator;
                    }
                }                  //module-translator
                leaf YANG_MODULE_TRANSLATOR {
                    type string;
                }                  //WORD
                leaf DAEMONS_LIST {
                    type enumeration {
                        enum babeld;
                        enum bgpd;
                        enum fabricd;
                        enum ldpd;
                        enum ospfd;
                        enum pbrd;
                        enum pimd;
                        enum ripngd;
                        enum vrrpd;
                        enum bfdd;
                        enum eigrpd;
                        enum isisd;
                        enum nhrpd;
                        enum ospf6d;
                        enum pathd;
                        enum pim6d;
                        enum ripd;
                        enum staticd;
                        enum zebra;
                    }
                }                  //<babeld|bgpd|fabricd|ldpd|ospfd|pbrd|pimd|ripngd|vrrpd|bfdd|eigrpd|isisd|nhrpd|ospf6d|pathd|pim6d|ripd|staticd|zebra> ['For the babeld daemon', 'For the bgpd daemon', 'For the fabricd daemon', 'For the ldpd daemon', 'For the ospfd daemon', 'For the pbrd daemon', 'For the pimd daemon', 'For the ripngd daemon', 'For the vrrpd daemon', 'For the bfdd daemon', 'For the eigrpd daemon', 'For the isisd daemon', 'For the nhrpd daemon', 'For the ospf6d daemon', 'For the pathd daemon', 'For the pim6d daemom', 'For the ripd daemon', 'For the staticd daemon', 'For the zebra daemon']
                leaf MODULE_NAME {
                    type string;
                }                  //WORD
                leaf CHOICE_CASE {
                    type enumeration {
                        enum compiled;
                        enum summary;
                        enum tree;
                        enum yang;
                        enum yin;
                    }
                }                  //<compiled|summary|tree|yang|yin> ['Display compiled module in YANG format', 'Display summary information about the module', 'Display module in the tree (RFC 8340) format', 'Display module in the YANG format', 'Display module in the YIN format']
            }
            container debug_bgp_evpn {
                leaf mh {
                    type enumeration {
                        enum mh;
                    }
                }                  //mh
                leaf CHOICE_CASE {
                    type enumeration {
                        enum es;
                        enum route;
                    }
                }                  //<es|route> ['Ethernet Segment debugging', 'Route debugging']
            }
            container debug_bgp_as4 {
                leaf segment {
                    type enumeration {
                        enum segment;
                    }
                }                  //segment
            }
            container debug_bgp_keepalives {
                leaf IP_ADDRESS {
                    type union {
                        type inet:ipv4-address;
                        type inet:ipv6-address;
                        type string;
                    }
                }                  //<A.B.C.D|X:X::X:X|WORD>
            }
            container debug_bgp_lptest {
                leaf clear {
                    type enumeration {
                        enum clear;
                    }
                }                  //clear
                leaf show {
                    type enumeration {
                        enum show;
                    }
                }                  //show
                leaf start {
                    type enumeration {
                        enum start;
                    }
                }                  //start
                leaf stop {
                    type enumeration {
                        enum stop;
                    }
                }                  //stop
            }
            container debug_bgp_neighbor-events {
                leaf IP_ADDRESS {
                    type union {
                        type inet:ipv4-address;
                        type inet:ipv6-address;
                        type string;
                    }
                }                  //<A.B.C.D|X:X::X:X|WORD>
            }
            container debug_bgp_pbr {
                leaf error {
                    type enumeration {
                        enum error;
                    }
                }                  //error
            }
            container debug_bgp_updates {
                leaf IN_OUT_BOUND {
                    type enumeration {
                        enum in;
                        enum out;
                    }
                }                  //<in|out> ['Inbound updates', 'Outbound updates']
                leaf IP_ADDRESS {
                    type union {
                        type inet:ipv4-address;
                        type inet:ipv6-address;
                        type string;
                    }
                }                  //<A.B.C.D|X:X::X:X|WORD>
            }
            container debug_bgp_zebra {
                leaf prefix {
                    type enumeration {
                        enum prefix;
                    }
                }                  //prefix
                leaf IPV4_PREFIX {
                    type union {
                        type inet:ipv4-prefix;
                        type inet:ipv6-prefix;
                    }
                }                  //<A.B.C.D/M|X:X::X:X/M>
            }
            container debug_mld_trace {
                leaf detail {
                    type enumeration {
                        enum detail;
                    }
                }                  //detail
            }
            container debug_northbound_callbacks {
                leaf configuration {
                    type enumeration {
                        enum configuration;
                    }
                }                  //configuration
                leaf state {
                    type enumeration {
                        enum state;
                    }
                }                  //state
                leaf rpc {
                    type enumeration {
                        enum rpc;
                    }
                }                  //rpc
            }
            container debug_northbound_client {
                leaf confd {
                    type enumeration {
                        enum confd;
                    }
                }                  //confd
                leaf sysrepo {
                    type enumeration {
                        enum sysrepo;
                    }
                }                  //sysrepo
            }
            container debug_ospf_ism {
                leaf NSM_STATUS_EVENT_TIMER {
                    type enumeration {
                        enum status;
                        enum events;
                        enum timers;
                    }
                }                  //<status|events|timers> ['ISM Status Information', 'ISM Event Information', 'ISM TImer Information']
            }
            container debug_ospf_lsa {
                leaf LSA_OPERATION_TYPE {
                    type enumeration {
                        enum generate;
                        enum flooding;
                        enum install;
                        enum refresh;
                        enum aggregate;
                    }
                }                  //<generate|flooding|install|refresh|aggregate> ['LSA Generation', 'LSA Flooding', 'LSA Install/Delete', 'LSA Refresh', 'External LSA Aggregation']
            }
            container debug_ospf_nsm {
                leaf NSM_STATUS_EVENT_TIMER {
                    type enumeration {
                        enum status;
                        enum events;
                        enum timers;
                    }
                }                  //<status|events|timers> ['NSM Status Information', 'NSM Event Information', 'NSM Timer Information']
            }
            container debug_ospf_zebra {
                leaf ZEBRA_INTERFACE_REDISTRIBUTE {
                    type enumeration {
                        enum interface;
                        enum redistribute;
                    }
                }                  //<interface|redistribute> ['Zebra interface', 'Zebra redistribute']
            }
            container debug_ospf6_lsa {
                leaf aggregation {
                    type enumeration {
                        enum aggregation;
                    }
                }                  //aggregation
                leaf all {
                    type enumeration {
                        enum all;
                    }
                }                  //all
                leaf CHOICE_CASE {
                    type enumeration {
                        enum router;
                        enum network;
                        enum inter-prefix;
                        enum inter-router;
                        enum as-external;
                        enum nssa;
                        enum link;
                        enum intra-prefix;
                        enum unknown;
                    }
                }                  //<router|network|inter-prefix|inter-router|as-external|nssa|link|intra-prefix|unknown> ['Display Router LSAs', 'Display Network LSAs', 'Display Inter-Area-Prefix LSAs', 'Display Inter-Router LSAs', 'Display As-External LSAs', 'Display NSSA LSAs', 'Display Link LSAs', 'Display Intra-Area-Prefix LSAs', 'Display LSAs of unknown origin']
            }
            container debug_ospf6_authentication {
                leaf CHOICE_CASE {
                    type enumeration {
                        enum tx;
                        enum rx;
                    }
                }                  //<tx|rx> ['debug authentication tx', 'debug authentication rx']
            }
            container debug_ospf6_border-routers {
                leaf area-id {
                    type enumeration {
                        enum area-id;
                    }
                }                  //area-id
                leaf SPECIFY_AREA-ID {
                    type inet:ipv4-address;
                }                  //A.B.C.D
                leaf router-id {
                    type enumeration {
                        enum router-id;
                    }
                }                  //router-id
                leaf SPECIFY_BORDER-ROUTER_ROUTER-ID {
                    type inet:ipv4-address;
                }                  //A.B.C.D
            }
            container debug_ospf6_neighbor {
                leaf CHOICE_CASE {
                    type enumeration {
                        enum state;
                        enum event;
                    }
                }                  //<state|event> ['Debug OSPFv3 Neighbor State Change', 'Debug OSPFv3 Neighbor Event']
            }
            container debug_ospf6_spf {
                leaf database {
                    type enumeration {
                        enum database;
                    }
                }                  //database
                leaf process {
                    type enumeration {
                        enum process;
                    }
                }                  //process
                leaf time {
                    type enumeration {
                        enum time;
                    }
                }                  //time
            }
            container debug_ospf6_zebra {
                leaf CHOICE_CASE {
                    type enumeration {
                        enum send;
                        enum recv;
                    }
                }                  //<send|recv> ['Debug Sending zebra', 'Debug Receiving zebra']
            }
            container debug_pim_nht {
                leaf detail {
                    type enumeration {
                        enum detail;
                    }
                }                  //detail
                leaf rp {
                    type enumeration {
                        enum rp;
                    }
                }                  //rp
            }
            container debug_pim_packet-dump {
                leaf receive {
                    type enumeration {
                        enum receive;
                    }
                }                  //receive
                leaf send {
                    type enumeration {
                        enum send;
                    }
                }                  //send
            }
            container debug_pim_packets {
                leaf CHOICE_CASE {
                    type enumeration {
                        enum hello;
                        enum joins;
                        enum register;
                    }
                }                  //<hello|joins|register> ['PIM Hello protocol packets', 'PIM Join/Prune protocol packets', 'PIM Register/Reg-Stop protocol packets']
            }
            container debug_pim_trace {
                leaf detail {
                    type enumeration {
                        enum detail;
                    }
                }                  //detail
            }
            container debug_pimv6_nht {
                leaf detail {
                    type enumeration {
                        enum detail;
                    }
                }                  //detail
            }
            container debug_pimv6_packet-dump {
                leaf receive {
                    type enumeration {
                        enum receive;
                    }
                }                  //receive
                leaf send {
                    type enumeration {
                        enum send;
                    }
                }                  //send
            }
            container debug_pimv6_packets {
                leaf CHOICE_CASE {
                    type enumeration {
                        enum hello;
                        enum joins;
                        enum register;
                    }
                }                  //<hello|joins|register> ['PIMv6 Hello protocol packets', 'PIMv6 Join/Prune protocol packets', 'PIMv6 Register/Reg-Stop protocol packets']
            }
            container debug_pimv6_trace {
                leaf detail {
                    type enumeration {
                        enum detail;
                    }
                }                  //detail
            }
            container debug_zebra_dplane {
                leaf detailed {
                    type enumeration {
                        enum detailed;
                    }
                }                  //detailed
            }
            container debug_zebra_evpn {
                leaf mh {
                    type enumeration {
                        enum mh;
                    }
                }                  //mh
                leaf CHOICE_CASE {
                    type enumeration {
                        enum es;
                        enum mac;
                        enum neigh;
                        enum nh;
                    }
                }                  //<es|mac|neigh|nh> ['Ethernet Segment Debugging', 'MAC Debugging', 'Neigh Debugging', 'Nexthop Debugging']
            }
            container debug_zebra_nexthop {
                leaf detail {
                    type enumeration {
                        enum detail;
                    }
                }                  //detail
            }
            container debug_zebra_mpls {
                leaf detailed {
                    type enumeration {
                        enum detailed;
                    }
                }                  //detailed
            }
            container debug_zebra_nht {
                leaf detailed {
                    type enumeration {
                        enum detailed;
                    }
                }                  //detailed
            }
            container debug_zebra_packet {
                leaf CHOICE_CASE {
                    type enumeration {
                        enum recv;
                        enum send;
                    }
                }                  //<recv|send> ['Debug option set for receive packet', 'Debug option set for send packet']
                leaf detail {
                    type enumeration {
                        enum detail;
                    }
                }                  //detail
            }
            container debug_zebra_rib {
                leaf detailed {
                    type enumeration {
                        enum detailed;
                    }
                }                  //detailed
            }
            container debug_igmp_trace {
                leaf detail {
                    type enumeration {
                        enum detail;
                    }
                }                  //detail
            }
            container debug_rfapi-dev_close {
                leaf rfd {
                    type enumeration {
                        enum rfd;
                    }
                }                  //rfd
                leaf RFAPI_HANDLE_IN_HEXADECIMAL {
                    type string;
                }                  //HANDLE
                leaf vn {
                    type enumeration {
                        enum vn;
                    }
                }                  //vn
                leaf IP_ADDRESS {
                    type union {
                        type inet:ipv4-address;
                        type inet:ipv6-address;
                    }
                }                  //<A.B.C.D|X:X::X:X>
                leaf un {
                    type enumeration {
                        enum un;
                    }
                }                  //un
            }
            container debug_rfapi-dev_open {
                leaf vn {
                    type enumeration {
                        enum vn;
                    }
                }                  //vn
                leaf IP_ADDRESS {
                    type union {
                        type inet:ipv4-address;
                        type inet:ipv6-address;
                    }
                }                  //<A.B.C.D|X:X::X:X>
                leaf un {
                    type enumeration {
                        enum un;
                    }
                }                  //un
            }
            container debug_rfapi-dev_query {
                leaf vn {
                    type enumeration {
                        enum vn;
                    }
                }                  //vn
                leaf IP_ADDRESS {
                    type union {
                        type inet:ipv4-address;
                        type inet:ipv6-address;
                    }
                }                  //<A.B.C.D|X:X::X:X>
                leaf un {
                    type enumeration {
                        enum un;
                    }
                }                  //un
                leaf lni {
                    type enumeration {
                        enum lni;
                    }
                }                  //lni
                leaf LOGICAL_NETWORK_ID {
                    type string;
                }                  //LNI
                leaf target {
                    type enumeration {
                        enum target;
                    }
                }                  //target
                leaf TARGET_MAC_ADDR {
                    type string;
                }                  //X:X:X:X:X:X
            }
            container debug_rfapi-dev_register {
                leaf vn {
                    type enumeration {
                        enum vn;
                    }
                }                  //vn
                leaf IP_ADDRESS {
                    type union {
                        type inet:ipv4-address;
                        type inet:ipv6-address;
                    }
                }                  //<A.B.C.D|X:X::X:X>
                leaf un {
                    type enumeration {
                        enum un;
                    }
                }                  //un
                leaf prefix {
                    type enumeration {
                        enum prefix;
                    }
                }                  //prefix
                leaf IPV4_PREFIX {
                    type union {
                        type inet:ipv4-prefix;
                        type inet:ipv6-prefix;
                    }
                }                  //<A.B.C.D/M|X:X::X:X/M>
                leaf lifetime {
                    type enumeration {
                        enum lifetime;
                    }
                }                  //lifetime
                leaf LIFETIME {
                    type string;
                }                  //SECONDS
                leaf cost {
                    type enumeration {
                        enum cost;
                    }
                }                  //cost
                leaf COST_VALUE {
                    type int32;
                }                  //(0-255)
                leaf macaddr {
                    type enumeration {
                        enum macaddr;
                    }
                }                  //macaddr
                leaf MAC_ADDRESS {
                    type string;
                }                  //X:X:X:X:X:X
                leaf lni {
                    type enumeration {
                        enum lni;
                    }
                }                  //lni
                leaf LNI_VALUE_RANGE {
                    type int32;
                }                  //(0-16777215)
            }
            container debug_rfapi-dev_unregister {
                leaf vn {
                    type enumeration {
                        enum vn;
                    }
                }                  //vn
                leaf IP_ADDRESS {
                    type union {
                        type inet:ipv4-address;
                        type inet:ipv6-address;
                    }
                }                  //<A.B.C.D|X:X::X:X>
                leaf un {
                    type enumeration {
                        enum un;
                    }
                }                  //un
                leaf prefix {
                    type enumeration {
                        enum prefix;
                    }
                }                  //prefix
                leaf IPV4_PREFIX {
                    type union {
                        type inet:ipv4-prefix;
                        type inet:ipv6-prefix;
                    }
                }                  //<A.B.C.D/M|X:X::X:X/M>
                leaf kill {
                    type enumeration {
                        enum kill;
                    }
                }                  //kill
            }
            container debug_rip_packet {
                leaf CHOICE_CASE {
                    type enumeration {
                        enum recv;
                        enum send;
                    }
                }                  //<recv|send> ['RIP receive packet', 'RIP send packet']
            }
            container debug_ripng_packet {
                leaf CHOICE_CASE {
                    type enumeration {
                        enum recv;
                        enum send;
                    }
                }                  //<recv|send> ['Debug option set for receive packet', 'Debug option set for send packet']
            }
            container clear_ip_bgp {
                leaf INSTANCE_VIEW_VRF {
                    type enumeration {
                        enum view;
                        enum vrf;
                    }
                }                  //<view|vrf> ['BGP view', 'BGP VRF']
                leaf VIEWVRF_NAME {
                    type string;
                }                  //VIEWVRFNAME
                leaf ipv6 {
                    type enumeration {
                        enum ipv6;
                    }
                }                  //ipv6
                leaf ADDRESS_FAMILY_MODIFIER {
                    type enumeration {
                        enum unicast;
                        enum multicast;
                        enum vpn;
                    }
                }                  //<unicast|multicast|vpn> ['Address Family modifier', 'Address Family modifier', 'Address Family modifier']
                leaf prefix {
                    type enumeration {
                        enum prefix;
                    }
                }                  //prefix
                leaf IPV6_PREFIX {
                    type inet:ipv6-prefix;
                }                  //X:X::X:X/M
            }
            container clear_ip_igmp {
                leaf vrf {
                    type enumeration {
                        enum vrf;
                    }
                }                  //vrf
                leaf THE_VRF_NAME {
                    type string;
                }                  //NAME
                leaf interfaces {
                    type enumeration {
                        enum interfaces;
                    }
                }                  //interfaces
            }
            container clear_ip_interfaces {
                leaf vrf {
                    type enumeration {
                        enum vrf;
                    }
                }                  //vrf
                leaf THE_VRF_NAME {
                    type string;
                }                  //NAME
            }
            container clear_ip_mroute {
                leaf vrf {
                    type enumeration {
                        enum vrf;
                    }
                }                  //vrf
                leaf THE_VRF_NAME {
                    type string;
                }                  //NAME
                leaf count {
                    type enumeration {
                        enum count;
                    }
                }                  //count
            }
            container clear_ip_ospf {
                leaf INSTANCE_ID {
                    type int32;
                }                  //(1-65535)
                leaf neighbor {
                    type enumeration {
                        enum neighbor;
                    }
                }                  //neighbor
                leaf process {
                    type enumeration {
                        enum process;
                    }
                }                  //process
                leaf vrf {
                    type enumeration {
                        enum vrf;
                    }
                }                  //vrf
                leaf THE_VRF_NAME {
                    type string;
                }                  //NAME
                leaf interface {
                    type enumeration {
                        enum interface;
                    }
                }                  //interface
            }
            container clear_ip_pim {
                leaf vrf {
                    type enumeration {
                        enum vrf;
                    }
                }                  //vrf
                leaf THE_VRF_NAME {
                    type string;
                }                  //NAME
                leaf bsr-data {
                    type enumeration {
                        enum bsr-data;
                    }
                }                  //bsr-data
                leaf interface_traffic {
                    type enumeration {
                        enum interface_traffic;
                    }
                }                  //traffic
                leaf interfaces {
                    type enumeration {
                        enum interfaces;
                    }
                }                  //interfaces
                leaf oil {
                    type enumeration {
                        enum oil;
                    }
                }                  //oil
            }
            container clear_ip_rip {
                leaf vrf {
                    type enumeration {
                        enum vrf;
                    }
                }                  //vrf
                leaf THE_VRF_NAME {
                    type string;
                }                  //WORD
            }
            container clear_ipv6_mroute {
                leaf vrf {
                    type enumeration {
                        enum vrf;
                    }
                }                  //vrf
                leaf THE_VRF_NAME {
                    type string;
                }                  //NAME
                leaf count {
                    type enumeration {
                        enum count;
                    }
                }                  //count
            }
            container clear_ipv6_pim {
                leaf vrf {
                    type enumeration {
                        enum vrf;
                    }
                }                  //vrf
                leaf THE_VRF_NAME {
                    type string;
                }                  //NAME
                leaf bsr-data {
                    type enumeration {
                        enum bsr-data;
                    }
                }                  //bsr-data
                leaf interface_traffic {
                    type enumeration {
                        enum interface_traffic;
                    }
                }                  //traffic
                leaf interfaces {
                    type enumeration {
                        enum interfaces;
                    }
                }                  //interfaces
                leaf oil {
                    type enumeration {
                        enum oil;
                    }
                }                  //oil
            }
            container clear_ipv6_ripng {
                leaf vrf {
                    type enumeration {
                        enum vrf;
                    }
                }                  //vrf
                leaf THE_VRF_NAME {
                    type string;
                }                  //WORD
            }
            container clear_bfd_peer {
                leaf PEER_LABEL {
                    type string;
                }                  //WORD
                leaf counters {
                    type enumeration {
                        enum counters;
                    }
                }                  //counters
                leaf IP_ADDRESS {
                    type union {
                        type inet:ipv4-address;
                        type inet:ipv6-address;
                    }
                }                  //<A.B.C.D|X:X::X:X>
                leaf multihop_counters {
                    type enumeration {
                        enum multihop_counters;
                    }
                }                  //counters
                leaf local-address {
                    type enumeration {
                        enum local-address;
                    }
                }                  //local-address
                leaf interface {
                    type enumeration {
                        enum interface;
                    }
                }                  //interface
                leaf CONFIGURE_LOCAL_INTERFACE_NAME {
                    type string;
                }                  //IFNAME
            }
            container clear_configuration_transactions {
                leaf oldest {
                    type enumeration {
                        enum oldest;
                    }
                }                  //oldest
                leaf NUMBER_OF_TRANSACTIONS_TO {
                    type int32;
                }                  //(1-100)
            }
            container clear_isis_neighbor {
                leaf SYSTEM_ID {
                    type string;
                }                  //WORD
            }
            container clear_route-map_counters {
                leaf ROUTE-MAP_NAME {
                    type string;
                }                  //RMAP_NAME
            }
            container clear_thread_cpu {
                leaf DISPLAY_FILTER {
                    type string;
                }                  //FILTER
            }
            container clear_vnc_nve {
                leaf FOR_ALL_NVES {
                    type string;
                }                  //*
                leaf un {
                    type enumeration {
                        enum un;
                    }
                }                  //un
                leaf IP_ADDRESS {
                    type union {
                        type string;
                        type inet:ipv4-address;
                        type inet:ipv6-address;
                    }
                }                  //<*|A.B.C.D|X:X::X:X>
                leaf vn {
                    type enumeration {
                        enum vn;
                    }
                }                  //vn
            }
            container clear_zebra_fpm {
                leaf stats {
                    type enumeration {
                        enum stats;
                    }
                }                  //stats
            }
            container no_match_ip_address {
                leaf IP_ACCESS-LIST_NAME {
                    type string;
                }                  //ACCESSLIST4_NAME
                leaf prefix-list {
                    type enumeration {
                        enum prefix-list;
                    }
                }                  //prefix-list
                leaf IP_PREFIX-LIST_NAME {
                    type string;
                }                  //PREFIXLIST_NAME
            }
            container no_match_ip_next-hop {
                leaf IP_ACCESS-LIST_NAME {
                    type string;
                }                  //ACCESSLIST4_NAME
                leaf prefix-list {
                    type enumeration {
                        enum prefix-list;
                    }
                }                  //prefix-list
                leaf IP_PREFIX-LIST_NAME {
                    type string;
                }                  //PREFIXLIST_NAME
            }
            container no_debug_bgp_evpn {
                leaf mh {
                    type enumeration {
                        enum mh;
                    }
                }                  //mh
                leaf CHOICE_CASE {
                    type enumeration {
                        enum es;
                        enum route;
                    }
                }                  //<es|route> ['Ethernet Segment debugging', 'Route debugging']
            }
            container no_debug_bgp_as4 {
                leaf segment {
                    type enumeration {
                        enum segment;
                    }
                }                  //segment
            }
            container no_debug_bgp_bestpath {
                leaf IPV4_PREFIX {
                    type union {
                        type inet:ipv4-prefix;
                        type inet:ipv6-prefix;
                    }
                }                  //<A.B.C.D/M|X:X::X:X/M>
            }
            container no_debug_bgp_keepalives {
                leaf IP_ADDRESS {
                    type union {
                        type inet:ipv4-address;
                        type inet:ipv6-address;
                        type string;
                    }
                }                  //<A.B.C.D|X:X::X:X|WORD>
            }
            container no_debug_bgp_neighbor-events {
                leaf IP_ADDRESS {
                    type union {
                        type inet:ipv4-address;
                        type inet:ipv6-address;
                        type string;
                    }
                }                  //<A.B.C.D|X:X::X:X|WORD>
            }
            container no_debug_bgp_pbr {
                leaf error {
                    type enumeration {
                        enum error;
                    }
                }                  //error
            }
            container no_debug_bgp_updates {
                leaf IN_OUT_BOUND {
                    type enumeration {
                        enum in;
                        enum out;
                    }
                }                  //<in|out> ['Inbound updates', 'Outbound updates']
                leaf IP_ADDRESS {
                    type union {
                        type inet:ipv4-address;
                        type inet:ipv6-address;
                        type string;
                    }
                }                  //<A.B.C.D|X:X::X:X|WORD>
            }
            container no_debug_bgp_zebra {
                leaf prefix {
                    type enumeration {
                        enum prefix;
                    }
                }                  //prefix
                leaf IPV4_PREFIX {
                    type union {
                        type inet:ipv4-prefix;
                        type inet:ipv6-prefix;
                    }
                }                  //<A.B.C.D/M|X:X::X:X/M>
            }
            container no_debug_mld_trace {
                leaf detail {
                    type enumeration {
                        enum detail;
                    }
                }                  //detail
            }
            container no_debug_northbound_callbacks {
                leaf configuration {
                    type enumeration {
                        enum configuration;
                    }
                }                  //configuration
                leaf state {
                    type enumeration {
                        enum state;
                    }
                }                  //state
                leaf rpc {
                    type enumeration {
                        enum rpc;
                    }
                }                  //rpc
            }
            container no_debug_northbound_client {
                leaf confd {
                    type enumeration {
                        enum confd;
                    }
                }                  //confd
                leaf sysrepo {
                    type enumeration {
                        enum sysrepo;
                    }
                }                  //sysrepo
            }
            container no_debug_ospf_ism {
                leaf NSM_STATUS_EVENT_TIMER {
                    type enumeration {
                        enum status;
                        enum events;
                        enum timers;
                    }
                }                  //<status|events|timers> ['ISM Status Information', 'ISM Event Information', 'ISM TImer Information']
            }
            container no_debug_ospf_lsa {
                leaf LSA_OPERATION_TYPE {
                    type enumeration {
                        enum generate;
                        enum flooding;
                        enum install;
                        enum refresh;
                        enum aggregate;
                    }
                }                  //<generate|flooding|install|refresh|aggregate> ['LSA Generation', 'LSA Flooding', 'LSA Install/Delete', 'LSA Refres', 'External LSA Aggregation']
            }
            container no_debug_ospf_nsm {
                leaf NSM_STATUS_EVENT_TIMER {
                    type enumeration {
                        enum status;
                        enum events;
                        enum timers;
                    }
                }                  //<status|events|timers> ['NSM Status Information', 'NSM Event Information', 'NSM Timer Information']
            }
            container no_debug_ospf_zebra {
                leaf ZEBRA_INTERFACE_REDISTRIBUTE {
                    type enumeration {
                        enum interface;
                        enum redistribute;
                    }
                }                  //<interface|redistribute> ['Zebra interface', 'Zebra redistribute']
            }
            container no_debug_ospf6_lsa {
                leaf aggregation {
                    type enumeration {
                        enum aggregation;
                    }
                }                  //aggregation
                leaf all {
                    type enumeration {
                        enum all;
                    }
                }                  //all
                leaf CHOICE_CASE {
                    type enumeration {
                        enum router;
                        enum network;
                        enum inter-prefix;
                        enum inter-router;
                        enum as-external;
                        enum nssa;
                        enum link;
                        enum intra-prefix;
                        enum unknown;
                    }
                }                  //<router|network|inter-prefix|inter-router|as-external|nssa|link|intra-prefix|unknown> ['Display Router LSAs', 'Display Network LSAs', 'Display Inter-Area-Prefix LSAs', 'Display Inter-Router LSAs', 'Display As-External LSAs', 'Display NSSA LSAs', 'Display Link LSAs', 'Display Intra-Area-Prefix LSAs', 'Display LSAs of unknown origin']
            }
            container no_debug_ospf6_authentication {
                leaf CHOICE_CASE {
                    type enumeration {
                        enum tx;
                        enum rx;
                    }
                }                  //<tx|rx> ['debug authentication tx', 'debug authentication rx']
            }
            container no_debug_ospf6_neighbor {
                leaf CHOICE_CASE {
                    type enumeration {
                        enum state;
                        enum event;
                    }
                }                  //<state|event> ['Debug OSPFv3 Neighbor State Change', 'Debug OSPFv3 Neighbor Event']
            }
            container no_debug_ospf6_spf {
                leaf database {
                    type enumeration {
                        enum database;
                    }
                }                  //database
                leaf process {
                    type enumeration {
                        enum process;
                    }
                }                  //process
                leaf time {
                    type enumeration {
                        enum time;
                    }
                }                  //time
            }
            container no_debug_ospf6_zebra {
                leaf CHOICE_CASE {
                    type enumeration {
                        enum send;
                        enum recv;
                    }
                }                  //<send|recv> ['Debug Sending zebra', 'Debug Receiving zebra']
            }
            container no_debug_pim_nht {
                leaf detail {
                    type enumeration {
                        enum detail;
                    }
                }                  //detail
                leaf rp {
                    type enumeration {
                        enum rp;
                    }
                }                  //rp
            }
            container no_debug_pim_packet-dump {
                leaf receive {
                    type enumeration {
                        enum receive;
                    }
                }                  //receive
                leaf send {
                    type enumeration {
                        enum send;
                    }
                }                  //send
            }
            container no_debug_pim_packets {
                leaf CHOICE_CASE {
                    type enumeration {
                        enum hello;
                        enum joins;
                        enum register;
                    }
                }                  //<hello|joins|register> ['PIM Hello protocol packets', 'PIM Join/Prune protocol packets', 'PIM Register/Reg-Stop protocol packets']
            }
            container no_debug_pim_trace {
                leaf detail {
                    type enumeration {
                        enum detail;
                    }
                }                  //detail
            }
            container no_debug_pimv6_nht {
                leaf detail {
                    type enumeration {
                        enum detail;
                    }
                }                  //detail
            }
            container no_debug_pimv6_packet-dump {
                leaf receive {
                    type enumeration {
                        enum receive;
                    }
                }                  //receive
                leaf send {
                    type enumeration {
                        enum send;
                    }
                }                  //send
            }
            container no_debug_pimv6_packets {
                leaf CHOICE_CASE {
                    type enumeration {
                        enum hello;
                        enum joins;
                        enum register;
                    }
                }                  //<hello|joins|register> ['PIMv6 Hello protocol packets', 'PIMv6 Join/Prune protocol packets', 'PIMv6 Register/Reg-Stop protocol packets']
            }
            container no_debug_pimv6_trace {
                leaf detail {
                    type enumeration {
                        enum detail;
                    }
                }                  //detail
            }
            container no_debug_zebra_evpn {
                leaf mh {
                    type enumeration {
                        enum mh;
                    }
                }                  //mh
                leaf CHOICE_CASE {
                    type enumeration {
                        enum es;
                        enum mac;
                        enum neigh;
                        enum nh;
                    }
                }                  //<es|mac|neigh|nh> ['Ethernet Segment Debugging', 'MAC Debugging', 'Neigh Debugging', 'Nexthop Debugging']
            }
            container no_debug_zebra_nexthop {
                leaf detail {
                    type enumeration {
                        enum detail;
                    }
                }                  //detail
            }
            container no_debug_zebra_mpls {
                leaf detailed {
                    type enumeration {
                        enum detailed;
                    }
                }                  //detailed
            }
            container no_debug_zebra_nht {
                leaf detailed {
                    type enumeration {
                        enum detailed;
                    }
                }                  //detailed
            }
            container no_debug_zebra_packet {
                leaf CHOICE_CASE {
                    type enumeration {
                        enum recv;
                        enum send;
                    }
                }                  //<recv|send> ['Debug option set for receive packet', 'Debug option set for send packet']
                leaf detail {
                    type enumeration {
                        enum detail;
                    }
                }                  //detail
            }
            container no_debug_zebra_rib {
                leaf detailed {
                    type enumeration {
                        enum detailed;
                    }
                }                  //detailed
            }
            container no_debug_all_bgp {
                leaf vnc {
                    type enumeration {
                        enum vnc;
                    }
                }                  //vnc
            }
            container no_debug_igmp_trace {
                leaf detail {
                    type enumeration {
                        enum detail;
                    }
                }                  //detail
            }
            container no_debug_rip_packet {
                leaf CHOICE_CASE {
                    type enumeration {
                        enum recv;
                        enum send;
                    }
                }                  //<recv|send> ['RIP option set for receive packet', 'RIP option set for send packet']
            }
            container no_debug_ripng_packet {
                leaf CHOICE_CASE {
                    type enumeration {
                        enum recv;
                        enum send;
                    }
                }                  //<recv|send> ['Debug option set for receive packet', 'Debug option set for send packet']
            }
            container show_ip_nhrp_cache {
                leaf json {
                    type enumeration {
                        enum json;
                    }
                }                  //json
            }
            container show_ip_nhrp_nhs {
                leaf json {
                    type enumeration {
                        enum json;
                    }
                }                  //json
            }
            container show_ip_nhrp_shortcut {
                leaf json {
                    type enumeration {
                        enum json;
                    }
                }                  //json
            }
            container show_ip_nhrp_opennhrp {
                leaf json {
                    type enumeration {
                        enum json;
                    }
                }                  //json
            }
            container show_ip_route_summary {
                leaf table {
                    type enumeration {
                        enum table;
                    }
                }                  //table
                leaf THE_TABLE_NUMBER {
                    type int32;
                }                  //(1-4294967295)
                leaf prefix {
                    type enumeration {
                        enum prefix;
                    }
                }                  //prefix
                leaf prefix_json {
                    type enumeration {
                        enum prefix_json;
                    }
                }                  //json
                leaf json {
                    type enumeration {
                        enum json;
                    }
                }                  //json
            }
            container show_ip_bgp_update-groups {
                leaf SPECIFIC_SUBGROUP_TO_DISPLAY {
                    type string;
                }                  //SUBGROUP-ID
                leaf ROUTING_QUEUE {
                    type enumeration {
                        enum advertise-queue;
                        enum advertised-routes;
                        enum packet-queue;
                    }
                }                  //<advertise-queue|advertised-routes|packet-queue> ['Advertisement queue', 'Announced routes', 'Packet queue']
                leaf json {
                    type enumeration {
                        enum json;
                    }
                }                  //json
                leaf statistics {
                    type enumeration {
                        enum statistics;
                    }
                }                  //statistics
            }
            container show_ip_bgp_route-leak {
                leaf json {
                    type enumeration {
                        enum json;
                    }
                }                  //json
            }
            container show_ip_bgp_all {
                leaf community-list {
                    type enumeration {
                        enum community-list;
                    }
                }                  //community-list
                leaf COMMUNITY-LIST_NAME {
                    type union {
                        type int32;
                        type string;
                    }
                }                  //<(1-500)|COMMUNITY_LIST_NAME>
                leaf exact-match {
                    type enumeration {
                        enum exact-match;
                    }
                }                  //exact-match
                leaf exact-match_wide {
                    type enumeration {
                        enum exact-match_wide;
                    }
                }                  //wide
                leaf json {
                    type enumeration {
                        enum json;
                    }
                }                  //json
                leaf json_detail {
                    type enumeration {
                        enum json_detail;
                    }
                }                  //detail
                leaf wide {
                    type enumeration {
                        enum wide;
                    }
                }                  //wide
                leaf exact-match_json {
                    type enumeration {
                        enum exact-match_json;
                    }
                }                  //exact-match_json
                leaf exact-match_json_detail {
                    type enumeration {
                        enum exact-match_json_detail;
                    }
                }                  //detail
                leaf filter-list {
                    type enumeration {
                        enum filter-list;
                    }
                }                  //filter-list
                leaf REGULAR_EXPRESSION_ACCESS_LIST {
                    type string;
                }                  //AS_PATH_FILTER_NAME
                leaf prefix-list {
                    type enumeration {
                        enum prefix-list;
                    }
                }                  //prefix-list
                leaf PREFIX-LIST_NAME {
                    type string;
                }                  //WORD
                leaf access-list {
                    type enumeration {
                        enum access-list;
                    }
                }                  //access-list
                leaf ACCESS-LIST_NAME {
                    type string;
                }                  //ACCESSLIST_NAME
                leaf route-map {
                    type enumeration {
                        enum route-map;
                    }
                }                  //route-map
                leaf A_ROUTE-MAP_TO_MATCH {
                    type string;
                }                  //RMAP_NAME
                leaf rpki {
                    type enumeration {
                        enum rpki;
                    }
                }                  //rpki
                leaf CHOICE_CASE {
                    type enumeration {
                        enum invalid;
                        enum valid;
                        enum notfound;
                    }
                }                  //<invalid|valid|notfound> ['A valid path as determined by rpki', 'A invalid path as determined by rpki', 'A path that has no rpki data']
                leaf version {
                    type enumeration {
                        enum version;
                    }
                }                  //version
                leaf VERSION_NUMBER_AND_ABOVE {
                    type int32;
                }                  //(1-4294967295)
                leaf alias {
                    type enumeration {
                        enum alias;
                    }
                }                  //alias
                leaf BGP_COMMUNITY_ALIAS {
                    type string;
                }                  //ALIAS_NAME
                leaf IPV4_PREFIX {
                    type inet:ipv4-prefix;
                }                  //A.B.C.D/M
                leaf longer-prefixes {
                    type enumeration {
                        enum longer-prefixes;
                    }
                }                  //longer-prefixes
                leaf longer-prefixes_wide {
                    type enumeration {
                        enum longer-prefixes_wide;
                    }
                }                  //wide
                leaf longer-prefixes_json {
                    type enumeration {
                        enum longer-prefixes_json;
                    }
                }                  //longer-prefixes_json
                leaf longer-prefixes_json_detail {
                    type enumeration {
                        enum longer-prefixes_json_detail;
                    }
                }                  //detail
                leaf IPV6_PREFIX {
                    type inet:ipv6-prefix;
                }                  //X:X::X:X/M
                leaf neighbors {
                    type enumeration {
                        enum neighbors;
                    }
                }                  //neighbors
                leaf IP_ADDRESS {
                    type union {
                        type inet:ipv4-address;
                        type inet:ipv6-address;
                        type string;
                    }
                }                  //<A.B.C.D|X:X::X:X|WORD>
                leaf BGP_NEIGHBOR_ROUTE_DIRECTION {
                    type enumeration {
                        enum advertised-routes;
                        enum received-routes;
                        enum filtered-routes;
                    }
                }                  //<advertised-routes|received-routes|filtered-routes> ['Display the routes advertised to a BGP neighbor', 'Display the received routes from neighbor', 'Display the filtered routes received from neighbor']
                leaf detail {
                    type enumeration {
                        enum detail;
                    }
                }                  //detail
                leaf detail_json {
                    type enumeration {
                        enum detail_json;
                    }
                }                  //json
                leaf detail_wide {
                    type enumeration {
                        enum detail_wide;
                    }
                }                  //wide
            }
            container show_ip_bgp_cidr-only {
                leaf wide {
                    type enumeration {
                        enum wide;
                    }
                }                  //wide
            }
            container show_ip_bgp_dampening {
                leaf CHOICE_CASE {
                    type enumeration {
                        enum flap-statistics;
                        enum dampened-paths;
                    }
                }                  //<flap-statistics|dampened-paths> ['Display flap statistics of routes', 'Display paths suppressed due to dampening']
                leaf json {
                    type enumeration {
                        enum json;
                    }
                }                  //json
                leaf json_detail {
                    type enumeration {
                        enum json_detail;
                    }
                }                  //detail
                leaf wide {
                    type enumeration {
                        enum wide;
                    }
                }                  //wide
            }
            container show_ip_bgp_community {
                leaf COMMUNITY_NUMBER {
                    type string;
                }                  //AA:NN
                leaf exact-match {
                    type enumeration {
                        enum exact-match;
                    }
                }                  //exact-match
                leaf exact-match_wide {
                    type enumeration {
                        enum exact-match_wide;
                    }
                }                  //wide
                leaf json {
                    type enumeration {
                        enum json;
                    }
                }                  //json
                leaf json_detail {
                    type enumeration {
                        enum json_detail;
                    }
                }                  //detail
                leaf wide {
                    type enumeration {
                        enum wide;
                    }
                }                  //wide
                leaf exact-match_json {
                    type enumeration {
                        enum exact-match_json;
                    }
                }                  //exact-match_json
                leaf exact-match_json_detail {
                    type enumeration {
                        enum exact-match_json_detail;
                    }
                }                  //detail
            }
            container show_ip_bgp_detail-routes {
                leaf wide {
                    type enumeration {
                        enum wide;
                    }
                }                  //wide
            }
            container show_ip_bgp_json {
                leaf detail {
                    type enumeration {
                        enum detail;
                    }
                }                  //detail
            }
            container show_ip_bgp_neighbors {
                leaf IP_ADDRESS {
                    type union {
                        type inet:ipv4-address;
                        type inet:ipv6-address;
                        type string;
                    }
                }                  //<A.B.C.D|X:X::X:X|WORD>
                leaf BGP_NEIGHBOR_ROUTE_DIRECTION {
                    type enumeration {
                        enum advertised-routes;
                        enum received-routes;
                        enum filtered-routes;
                    }
                }                  //<advertised-routes|received-routes|filtered-routes> ['Display the routes advertised to a BGP neighbor', 'Display the received routes from neighbor', 'Display the filtered routes received from neighbor']
                leaf route-map {
                    type enumeration {
                        enum route-map;
                    }
                }                  //route-map
                leaf NAME_OF_THE_ROUTE {
                    type string;
                }                  //RMAP_NAME
                leaf detail {
                    type enumeration {
                        enum detail;
                    }
                }                  //detail
                leaf detail_json {
                    type enumeration {
                        enum detail_json;
                    }
                }                  //json
                leaf detail_wide {
                    type enumeration {
                        enum detail_wide;
                    }
                }                  //wide
                leaf json {
                    type enumeration {
                        enum json;
                    }
                }                  //json
                leaf wide {
                    type enumeration {
                        enum wide;
                    }
                }                  //wide
                leaf BGP_NEIGHBOR_ROUTE_STATS {
                    type enumeration {
                        enum flap-statistics;
                        enum dampened-routes;
                        enum routes;
                    }
                }                  //<flap-statistics|dampened-routes|routes> ['Display flap statistics of the routes learned from neighbor', 'Display the dampened routes received from neighbor', 'Display routes learned from neighbor']
                leaf bestpath-routes {
                    type enumeration {
                        enum bestpath-routes;
                    }
                }                  //bestpath-routes
                leaf bestpath-routes_json {
                    type enumeration {
                        enum bestpath-routes_json;
                    }
                }                  //json
                leaf bestpath-routes_wide {
                    type enumeration {
                        enum bestpath-routes_wide;
                    }
                }                  //wide
                leaf prefix-counts {
                    type enumeration {
                        enum prefix-counts;
                    }
                }                  //prefix-counts
                leaf prefix-counts_json {
                    type enumeration {
                        enum prefix-counts_json;
                    }
                }                  //json
                leaf received_prefix-filter {
                    type enumeration {
                        enum received_prefix-filter;
                    }
                }                  //received_prefix-filter
                leaf received_prefix-filter_json {
                    type enumeration {
                        enum received_prefix-filter_json;
                    }
                }                  //json
            }
            container show_ip_bgp_summary {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_ip_bgp_large-community {
                leaf LARGE_COMMUNITY {
                    type string;
                }                  //AA:BB:CC
                leaf exact-match {
                    type enumeration {
                        enum exact-match;
                    }
                }                  //exact-match
                leaf exact-match_json {
                    type enumeration {
                        enum exact-match_json;
                    }
                }                  //json
                leaf json {
                    type enumeration {
                        enum json;
                    }
                }                  //json
            }
            container show_ip_bgp_statistics {
                leaf json {
                    type enumeration {
                        enum json;
                    }
                }                  //json
            }
            container show_ip_bgp_detail {
                leaf json {
                    type enumeration {
                        enum json;
                    }
                }                  //json
            }
            container show_ip_bgp_peer-group {
                leaf PEER_GROUP_NAME {
                    type string;
                }                  //PGNAME
                leaf json {
                    type enumeration {
                        enum json;
                    }
                }                  //json
            }
            container show_ip_bgp_statistics-all {
                leaf json {
                    type enumeration {
                        enum json;
                    }
                }                  //json
            }
            container show_ip_bgp_vrfs {
                leaf SPECIFIC_VRF_NAME {
                    type string;
                }                  //VRFNAME
                leaf json {
                    type enumeration {
                        enum json;
                    }
                }                  //json
            }
            container show_ip_igmp_vrf {
                leaf THE_VRF_NAME {
                    type string;
                }                  //NAME
                leaf groups {
                    type enumeration {
                        enum groups;
                    }
                }                  //groups
                leaf groups_json {
                    type enumeration {
                        enum groups_json;
                    }
                }                  //json
                leaf groups_retransmissions {
                    type enumeration {
                        enum groups_retransmissions;
                    }
                }                  //retransmissions
                leaf interface {
                    type enumeration {
                        enum interface;
                    }
                }                  //interface
                leaf interface_json {
                    type enumeration {
                        enum interface_json;
                    }
                }                  //json
                leaf join {
                    type enumeration {
                        enum join;
                    }
                }                  //join
                leaf join_json {
                    type enumeration {
                        enum join_json;
                    }
                }                  //json
                leaf sources {
                    type enumeration {
                        enum sources;
                    }
                }                  //sources
                leaf sources_json {
                    type enumeration {
                        enum sources_json;
                    }
                }                  //json
                leaf sources_retransmissions {
                    type enumeration {
                        enum sources_retransmissions;
                    }
                }                  //retransmissions
                leaf statistics {
                    type enumeration {
                        enum statistics;
                    }
                }                  //statistics
                leaf statistics_interface {
                    type enumeration {
                        enum statistics_interface;
                    }
                }                  //interface
                leaf IGMP_INTERFACE {
                    type string;
                }                  //WORD
                leaf json {
                    type enumeration {
                        enum json;
                    }
                }                  //json
                leaf statistics_json {
                    type enumeration {
                        enum statistics_json;
                    }
                }                  //json
                leaf interface_detail {
                    type enumeration {
                        enum interface_detail;
                    }
                }                  //interface_detail
                leaf interface_detail_json {
                    type enumeration {
                        enum interface_detail_json;
                    }
                }                  //json
            }
            container show_ip_igmp_groups {
                leaf json {
                    type enumeration {
                        enum json;
                    }
                }                  //json
                leaf retransmissions {
                    type enumeration {
                        enum retransmissions;
                    }
                }                  //retransmissions
            }
            container show_ip_igmp_interface {
                leaf INTERFACE_NAME {
                    type string;
                }                  //WORD
                leaf json {
                    type enumeration {
                        enum json;
                    }
                }                  //json
            }
            container show_ip_igmp_join {
                leaf json {
                    type enumeration {
                        enum json;
                    }
                }                  //json
            }
            container show_ip_igmp_sources {
                leaf json {
                    type enumeration {
                        enum json;
                    }
                }                  //json
                leaf retransmissions {
                    type enumeration {
                        enum retransmissions;
                    }
                }                  //retransmissions
            }
            container show_ip_igmp_statistics {
                leaf interface {
                    type enumeration {
                        enum interface;
                    }
                }                  //interface
                leaf IGMP_INTERFACE {
                    type string;
                }                  //WORD
                leaf json {
                    type enumeration {
                        enum json;
                    }
                }                  //json
            }
            container show_ip_mroute_vrf {
                leaf THE_VRF_NAME {
                    type string;
                }                  //NAME
                leaf THE_SOURCE_OR_GROUP {
                    type inet:ipv4-address;
                }                  //A.B.C.D
                leaf THE_GROUP {
                    type inet:ipv4-address;
                }                  //A.B.C.D
                leaf fill {
                    type enumeration {
                        enum fill;
                    }
                }                  //fill
                leaf fill_json {
                    type enumeration {
                        enum fill_json;
                    }
                }                  //json
                leaf json {
                    type enumeration {
                        enum json;
                    }
                }                  //json
                leaf count {
                    type enumeration {
                        enum count;
                    }
                }                  //count
                leaf count_json {
                    type enumeration {
                        enum count_json;
                    }
                }                  //json
                leaf summary {
                    type enumeration {
                        enum summary;
                    }
                }                  //summary
                leaf summary_json {
                    type enumeration {
                        enum summary_json;
                    }
                }                  //json
            }
            container show_ip_mroute_fill {
                leaf json {
                    type enumeration {
                        enum json;
                    }
                }                  //json
            }
            container show_ip_mroute_count {
                leaf json {
                    type enumeration {
                        enum json;
                    }
                }                  //json
            }
            container show_ip_mroute_summary {
                leaf json {
                    type enumeration {
                        enum json;
                    }
                }                  //json
            }
            container show_ip_msdp_vrf {
                leaf THE_VRF_NAME {
                    type string;
                }                  //NAME
                leaf mesh-group {
                    type enumeration {
                        enum mesh-group;
                    }
                }                  //mesh-group
                leaf mesh-group_json {
                    type enumeration {
                        enum mesh-group_json;
                    }
                }                  //json
                leaf peer {
                    type enumeration {
                        enum peer;
                    }
                }                  //peer
                leaf peer_json {
                    type enumeration {
                        enum peer_json;
                    }
                }                  //json
                leaf sa {
                    type enumeration {
                        enum sa;
                    }
                }                  //sa
                leaf sa_json {
                    type enumeration {
                        enum sa_json;
                    }
                }                  //json
                leaf peer_detail {
                    type enumeration {
                        enum peer_detail;
                    }
                }                  //peer_detail
                leaf peer_detail_json {
                    type enumeration {
                        enum peer_detail_json;
                    }
                }                  //json
                leaf sa_detail {
                    type enumeration {
                        enum sa_detail;
                    }
                }                  //sa_detail
                leaf sa_detail_json {
                    type enumeration {
                        enum sa_detail_json;
                    }
                }                  //json
            }
            container show_ip_msdp_mesh-group {
                leaf json {
                    type enumeration {
                        enum json;
                    }
                }                  //json
            }
            container show_ip_msdp_peer {
                leaf PEER_IP_ADDRESS {
                    type inet:ipv4-address;
                }                  //A.B.C.D
                leaf json {
                    type enumeration {
                        enum json;
                    }
                }                  //json
            }
            container show_ip_msdp_sa {
                leaf SOURCE_OR_GROUP_IP {
                    type inet:ipv4-address;
                }                  //A.B.C.D
                leaf GROUP_IP {
                    type inet:ipv4-address;
                }                  //A.B.C.D
                leaf json {
                    type enumeration {
                        enum json;
                    }
                }                  //json
            }
            container show_ip_multicast_vrf {
                leaf THE_VRF_NAME {
                    type string;
                }                  //NAME
                leaf all {
                    type enumeration {
                        enum all;
                    }
                }                  //all
            }
            container show_ip_multicast_count {
                leaf json {
                    type enumeration {
                        enum json;
                    }
                }                  //json
            }
            container show_ip_nht_vrf {
                leaf THE_VRF_NAME {
                    type string;
                }                  //NAME
                leaf IP_ADDRESS {
                    type union {
                        type inet:ipv4-address;
                        type inet:ipv6-address;
                    }
                }                  //<A.B.C.D|X:X::X:X>
                leaf mrib {
                    type enumeration {
                        enum mrib;
                    }
                }                  //mrib
                leaf mrib_json {
                    type enumeration {
                        enum mrib_json;
                    }
                }                  //json
                leaf json {
                    type enumeration {
                        enum json;
                    }
                }                  //json
            }
            container show_ip_nht_mrib {
                leaf json {
                    type enumeration {
                        enum json;
                    }
                }                  //json
            }
            container show_ip_nht_route-map {
                leaf vrf {
                    type enumeration {
                        enum vrf;
                    }
                }                  //vrf
                leaf THE_VRF_NAME {
                    type string;
                }                  //NAME
                leaf all {
                    type enumeration {
                        enum all;
                    }
                }
                leaf json {
                    type enumeration {
                        enum json;
                    }
                }                  //json
            }
            container show_ip_import-check_vrf {
                leaf THE_VRF_NAME {
                    type string;
                }                  //NAME
                leaf IP_ADDRESS {
                    type union {
                        type inet:ipv4-address;
                        type inet:ipv6-address;
                    }
                }                  //<A.B.C.D|X:X::X:X>
                leaf mrib {
                    type enumeration {
                        enum mrib;
                    }
                }                  //mrib
                leaf mrib_json {
                    type enumeration {
                        enum mrib_json;
                    }
                }                  //json
                leaf json {
                    type enumeration {
                        enum json;
                    }
                }                  //json
            }
            container show_ip_import-check_mrib {
                leaf json {
                    type enumeration {
                        enum json;
                    }
                }                  //json
            }
            container show_ip_ospf_vrf {
                leaf THE_VRF_NAME {
                    type string;
                }                  //NAME
                leaf neighbor {
                    type enumeration {
                        enum neighbor;
                    }
                }                  //neighbor
                leaf INTERFACE_NAME {
                    type string;
                }                  //IFNAME
                leaf json {
                    type enumeration {
                        enum json;
                    }
                }                  //json
                leaf border-routers {
                    type enumeration {
                        enum border-routers;
                    }
                }                  //border-routers
                leaf border-routers_json {
                    type enumeration {
                        enum border-routers_json;
                    }
                }                  //json
                leaf database {
                    type enumeration {
                        enum database;
                    }
                }                  //database
                leaf OSPF_LSA_TYPE {
                    type enumeration {
                        enum asbr-summary;
                        enum external;
                        enum network;
                        enum router;
                        enum summary;
                        enum nssa-external;
                        enum opaque-link;
                        enum opaque-area;
                        enum opaque-as;
                    }
                }                  //<asbr-summary|external|network|router|summary|nssa-external|opaque-link|opaque-area|opaque-as> ['ASBR summary link states', 'External link states', 'Network link states', 'Router link states', 'Network summary link states', 'NSSA external link state', 'Link local Opaque-LSA', 'Link area Opaque-LSA', 'Link AS Opaque-LSA']
                leaf adv-router {
                    type inet:ipv4-address;
                }                  //A.B.C.D
                leaf self-originate {
                    type enumeration {
                        enum self-originate;
                    }
                }
                leaf LINK_STATE_ID {
                    type inet:ipv4-address;
                }                  //A.B.C.D
                leaf LSA_STATUS {
                    type enumeration {
                        enum max-age;
                        enum self-originate;
                    }
                }                  //<max-age|self-originate> ['LSAs in MaxAge list', 'Self-originated link states']
                leaf database_json {
                    type enumeration {
                        enum database_json;
                    }
                }                  //json
                leaf interface {
                    type enumeration {
                        enum interface;
                    }
                }                  //interface
                leaf interface_json {
                    type enumeration {
                        enum interface_json;
                    }
                }                  //json
                leaf neighbor_json {
                    type enumeration {
                        enum neighbor_json;
                    }
                }                  //json
                leaf reachable-routers {
                    type enumeration {
                        enum reachable-routers;
                    }
                }                  //reachable-routers
                leaf route {
                    type enumeration {
                        enum route;
                    }
                }                  //route
                leaf route_json {
                    type enumeration {
                        enum route_json;
                    }
                }                  //json
                leaf summary-address {
                    type enumeration {
                        enum summary-address;
                    }
                }                  //summary-address
                leaf summary-address_json {
                    type enumeration {
                        enum summary-address_json;
                    }
                }                  //json
                leaf graceful-restart_helper {
                    type enumeration {
                        enum graceful-restart_helper;
                    }
                }                  //graceful-restart_helper
                leaf graceful-restart_helper_json {
                    type enumeration {
                        enum graceful-restart_helper_json;
                    }
                }                  //json
                leaf interface_traffic {
                    type enumeration {
                        enum interface_traffic;
                    }
                }                  //interface_traffic
                leaf interface_traffic_json {
                    type enumeration {
                        enum interface_traffic_json;
                    }
                }                  //json
                leaf mpls-te_interface {
                    type enumeration {
                        enum mpls-te_interface;
                    }
                }                  //mpls-te_interface
                leaf neighbor_all {
                    type enumeration {
                        enum neighbor_all;
                    }
                }                  //neighbor_all
                leaf neighbor_all_json {
                    type enumeration {
                        enum neighbor_all_json;
                    }
                }                  //json
                leaf neighbor_detail {
                    type enumeration {
                        enum neighbor_detail;
                    }
                }                  //neighbor_detail
                leaf neighbor_detail_json {
                    type enumeration {
                        enum neighbor_detail_json;
                    }
                }                  //json
                leaf summary-address_detail {
                    type enumeration {
                        enum summary-address_detail;
                    }
                }                  //summary-address_detail
                leaf summary-address_detail_json {
                    type enumeration {
                        enum summary-address_detail_json;
                    }
                }                  //json
                leaf graceful-restart_helper_detail {
                    type enumeration {
                        enum graceful-restart_helper_detail;
                    }
                }                  //graceful-restart_helper_detail
                leaf graceful-restart_helper_detail_json {
                    type enumeration {
                        enum graceful-restart_helper_detail_json;
                    }
                }                  //json
                leaf neighbor_detail_all {
                    type enumeration {
                        enum neighbor_detail_all;
                    }
                }                  //neighbor_detail_all
                leaf neighbor_detail_all_json {
                    type enumeration {
                        enum neighbor_detail_all_json;
                    }
                }                  //json
            }
            container show_ip_ospf_neighbor {
                leaf INTERFACE_NAME {
                    type string;
                }                  //IFNAME
                leaf json {
                    type enumeration {
                        enum json;
                    }
                }                  //json
                leaf detail {
                    type enumeration {
                        enum detail;
                    }
                }                  //detail
                leaf detail_json {
                    type enumeration {
                        enum detail_json;
                    }
                }                  //json
                leaf NEIGHBOR_ID {
                    type inet:ipv4-address;
                }                  //A.B.C.D
            }
            container show_ip_ospf_border-routers {
                leaf json {
                    type enumeration {
                        enum json;
                    }
                }                  //json
            }
            container show_ip_ospf_database {
                leaf OSPF_LSA_TYPE {
                    type enumeration {
                        enum asbr-summary;
                        enum external;
                        enum network;
                        enum router;
                        enum summary;
                        enum nssa-external;
                        enum opaque-link;
                        enum opaque-area;
                        enum opaque-as;
                    }
                }                  //<asbr-summary|external|network|router|summary|nssa-external|opaque-link|opaque-area|opaque-as> ['ASBR summary link states', 'External link states', 'Network link states', 'Router link states', 'Network summary link states', 'NSSA external link state', 'Link local Opaque-LSA', 'Link area Opaque-LSA', 'Link AS Opaque-LSA']
                leaf adv-router {
                    type inet:ipv4-address;
                }                  //A.B.C.D
                leaf self-originate {
                    type enumeration {
                        enum self-originate;
                    }
                }
                leaf json {
                    type enumeration {
                        enum json;
                    }
                }                  //json
                leaf LINK_STATE_ID {
                    type inet:ipv4-address;
                }                  //A.B.C.D
                leaf LSA_STATUS {
                    type enumeration {
                        enum max-age;
                        enum self-originate;
                    }
                }                  //<max-age|self-originate> ['LSAs in MaxAge list', 'Self-originated link states']
            }
            container show_ip_ospf_interface {
                leaf INTERFACE_NAME {
                    type string;
                }                  //INTERFACE
                leaf json {
                    type enumeration {
                        enum json;
                    }
                }                  //json
            }
            container show_ip_ospf_mpls-te {
                leaf router {
                    type enumeration {
                        enum router;
                    }
                }                  //router
            }
            container show_ip_ospf_route {
                leaf json {
                    type enumeration {
                        enum json;
                    }
                }                  //json
            }
            container show_ip_ospf_summary-address {
                leaf json {
                    type enumeration {
                        enum json;
                    }
                }                  //json
            }
            container show_ip_ospf_router-info {
                leaf pce {
                    type enumeration {
                        enum pce;
                    }
                }                  //pce
            }
            container show_ip_ospf_vrfs {
                leaf json {
                    type enumeration {
                        enum json;
                    }
                }                  //json
            }
            container show_ip_pim_vrf {
                leaf THE_VRF_NAME {
                    type string;
                }                  //NAME
                leaf interface {
                    type enumeration {
                        enum interface;
                    }
                }                  //interface
                leaf interface_json {
                    type enumeration {
                        enum interface_json;
                    }
                }                  //json
                leaf assert {
                    type enumeration {
                        enum assert;
                    }
                }                  //assert
                leaf assert-internal {
                    type enumeration {
                        enum assert-internal;
                    }
                }                  //assert-internal
                leaf assert-metric {
                    type enumeration {
                        enum assert-metric;
                    }
                }                  //assert-metric
                leaf assert-winner-metric {
                    type enumeration {
                        enum assert-winner-metric;
                    }
                }                  //assert-winner-metric
                leaf channel {
                    type enumeration {
                        enum channel;
                    }
                }                  //channel
                leaf channel_json {
                    type enumeration {
                        enum channel_json;
                    }
                }                  //json
                leaf group-type {
                    type enumeration {
                        enum group-type;
                    }
                }                  //group-type
                leaf group-type_json {
                    type enumeration {
                        enum group-type_json;
                    }
                }                  //json
                leaf join {
                    type enumeration {
                        enum join;
                    }
                }                  //join
                leaf join_json {
                    type enumeration {
                        enum join_json;
                    }
                }                  //json
                leaf jp-agg {
                    type enumeration {
                        enum jp-agg;
                    }
                }                  //jp-agg
                leaf local-membership {
                    type enumeration {
                        enum local-membership;
                    }
                }                  //local-membership
                leaf local-membership_json {
                    type enumeration {
                        enum local-membership_json;
                    }
                }                  //json
                leaf neighbor {
                    type enumeration {
                        enum neighbor;
                    }
                }                  //neighbor
                leaf neighbor_json {
                    type enumeration {
                        enum neighbor_json;
                    }
                }                  //json
                leaf nexthop {
                    type enumeration {
                        enum nexthop;
                    }
                }                  //nexthop
                leaf nexthop_json {
                    type enumeration {
                        enum nexthop_json;
                    }
                }                  //json
                leaf nexthop-lookup {
                    type enumeration {
                        enum nexthop-lookup;
                    }
                }                  //nexthop-lookup
                leaf SOURCERP_ADDRESS {
                    type inet:ipv4-address;
                }                  //A.B.C.D
                leaf MULTICAST_GROUP_ADDRESS {
                    type inet:ipv4-address;
                }                  //A.B.C.D
                leaf rp-info {
                    type enumeration {
                        enum rp-info;
                    }
                }                  //rp-info
                leaf rp-info_json {
                    type enumeration {
                        enum rp-info_json;
                    }
                }                  //json
                leaf rpf {
                    type enumeration {
                        enum rpf;
                    }
                }                  //rpf
                leaf rpf_json {
                    type enumeration {
                        enum rpf_json;
                    }
                }                  //json
                leaf secondary {
                    type enumeration {
                        enum secondary;
                    }
                }                  //secondary
                leaf state {
                    type enumeration {
                        enum state;
                    }
                }                  //state
                leaf state_json {
                    type enumeration {
                        enum state_json;
                    }
                }                  //json
                leaf statistics {
                    type enumeration {
                        enum statistics;
                    }
                }                  //statistics
                leaf statistics_interface {
                    type enumeration {
                        enum statistics_interface;
                    }
                }                  //interface
                leaf PIM_INTERFACE {
                    type string;
                }                  //WORD
                leaf json {
                    type enumeration {
                        enum json;
                    }
                }                  //json
                leaf statistics_json {
                    type enumeration {
                        enum statistics_json;
                    }
                }                  //json
                leaf upstream {
                    type enumeration {
                        enum upstream;
                    }
                }                  //upstream
                leaf upstream_json {
                    type enumeration {
                        enum upstream_json;
                    }
                }                  //json
                leaf upstream-join-desired {
                    type enumeration {
                        enum upstream-join-desired;
                    }
                }                  //upstream-join-desired
                leaf upstream-join-desired_json {
                    type enumeration {
                        enum upstream-join-desired_json;
                    }
                }                  //json
                leaf upstream-rpf {
                    type enumeration {
                        enum upstream-rpf;
                    }
                }                  //upstream-rpf
                leaf upstream-rpf_json {
                    type enumeration {
                        enum upstream-rpf_json;
                    }
                }                  //json
                leaf vxlan-groups {
                    type enumeration {
                        enum vxlan-groups;
                    }
                }                  //vxlan-groups
                leaf vxlan-groups_json {
                    type enumeration {
                        enum vxlan-groups_json;
                    }
                }                  //json
                leaf vxlan-work {
                    type enumeration {
                        enum vxlan-work;
                    }
                }                  //vxlan-work
                leaf vxlan-work_json {
                    type enumeration {
                        enum vxlan-work_json;
                    }
                }                  //json
                leaf interface_detail {
                    type enumeration {
                        enum interface_detail;
                    }
                }                  //interface_detail
                leaf interface_detail_json {
                    type enumeration {
                        enum interface_detail_json;
                    }
                }                  //json
                leaf interface_traffic {
                    type enumeration {
                        enum interface_traffic;
                    }
                }                  //interface_traffic
                leaf interface_traffic_json {
                    type enumeration {
                        enum interface_traffic_json;
                    }
                }                  //json
                leaf mlag_upstream {
                    type enumeration {
                        enum mlag_upstream;
                    }
                }                  //mlag_upstream
                leaf mlag_upstream_json {
                    type enumeration {
                        enum mlag_upstream_json;
                    }
                }                  //json
                leaf neighbor_detail {
                    type enumeration {
                        enum neighbor_detail;
                    }
                }                  //neighbor_detail
                leaf neighbor_detail_json {
                    type enumeration {
                        enum neighbor_detail_json;
                    }
                }                  //json
            }
            container show_ip_pim_interface {
                leaf INTERFACE_NAME {
                    type string;
                }                  //WORD
                leaf json {
                    type enumeration {
                        enum json;
                    }
                }                  //json
            }
            container show_ip_pim_channel {
                leaf json {
                    type enumeration {
                        enum json;
                    }
                }                  //json
            }
            container show_ip_pim_group-type {
                leaf GROUP_ADDRESS {
                    type inet:ipv4-address;
                }                  //A.B.C.D
                leaf json {
                    type enumeration {
                        enum json;
                    }
                }                  //json
            }
            container show_ip_pim_join {
                leaf THE_SOURCE_OR_GROUP {
                    type inet:ipv4-address;
                }                  //A.B.C.D
                leaf THE_GROUP {
                    type inet:ipv4-address;
                }                  //A.B.C.D
                leaf json {
                    type enumeration {
                        enum json;
                    }
                }                  //json
            }
            container show_ip_pim_local-membership {
                leaf json {
                    type enumeration {
                        enum json;
                    }
                }                  //json
            }
            container show_ip_pim_neighbor {
                leaf NAME_OF_INTERFACE_OR {
                    type string;
                }                  //WORD
                leaf json {
                    type enumeration {
                        enum json;
                    }
                }                  //json
            }
            container show_ip_pim_nexthop {
                leaf json {
                    type enumeration {
                        enum json;
                    }
                }                  //json
            }
            container show_ip_pim_rp-info {
                leaf IPV4_PREFIX {
                    type inet:ipv4-prefix;
                }                  //A.B.C.D/M
                leaf json {
                    type enumeration {
                        enum json;
                    }
                }                  //json
            }
            container show_ip_pim_rpf {
                leaf json {
                    type enumeration {
                        enum json;
                    }
                }                  //json
            }
            container show_ip_pim_state {
                leaf UNICAST_OR_MULTICAST_ADDRESS {
                    type inet:ipv4-address;
                }                  //A.B.C.D
                leaf MULTICAST_ADDRESS {
                    type inet:ipv4-address;
                }                  //A.B.C.D
                leaf json {
                    type enumeration {
                        enum json;
                    }
                }                  //json
            }
            container show_ip_pim_statistics {
                leaf interface {
                    type enumeration {
                        enum interface;
                    }
                }                  //interface
                leaf PIM_INTERFACE {
                    type string;
                }                  //WORD
                leaf json {
                    type enumeration {
                        enum json;
                    }
                }                  //json
            }
            container show_ip_pim_upstream {
                leaf THE_SOURCE_OR_GROUP {
                    type inet:ipv4-address;
                }                  //A.B.C.D
                leaf THE_GROUP {
                    type inet:ipv4-address;
                }                  //A.B.C.D
                leaf json {
                    type enumeration {
                        enum json;
                    }
                }                  //json
            }
            container show_ip_pim_upstream-join-desired {
                leaf json {
                    type enumeration {
                        enum json;
                    }
                }                  //json
            }
            container show_ip_pim_upstream-rpf {
                leaf json {
                    type enumeration {
                        enum json;
                    }
                }                  //json
            }
            container show_ip_pim_vxlan-groups {
                leaf SOURCE_OR_GROUP_IP {
                    type inet:ipv4-address;
                }                  //A.B.C.D
                leaf GROUP_IP {
                    type inet:ipv4-address;
                }                  //A.B.C.D
                leaf json {
                    type enumeration {
                        enum json;
                    }
                }                  //json
            }
            container show_ip_pim_vxlan-work {
                leaf json {
                    type enumeration {
                        enum json;
                    }
                }                  //json
            }
            container show_ip_pim_bsm-database {
                leaf vrf {
                    type enumeration {
                        enum vrf;
                    }
                }                  //vrf
                leaf THE_VRF_NAME {
                    type string;
                }                  //NAME
                leaf json {
                    type enumeration {
                        enum json;
                    }
                }                  //json
            }
            container show_ip_pim_bsr {
                leaf vrf {
                    type enumeration {
                        enum vrf;
                    }
                }                  //vrf
                leaf THE_VRF_NAME {
                    type string;
                }                  //NAME
                leaf json {
                    type enumeration {
                        enum json;
                    }
                }                  //json
            }
            container show_ip_pim_bsrp-info {
                leaf vrf {
                    type enumeration {
                        enum vrf;
                    }
                }                  //vrf
                leaf THE_VRF_NAME {
                    type string;
                }                  //NAME
                leaf json {
                    type enumeration {
                        enum json;
                    }
                }                  //json
            }
            container show_ipv6_nhrp_cache {
                leaf json {
                    type enumeration {
                        enum json;
                    }
                }                  //json
            }
            container show_ipv6_nhrp_nhs {
                leaf json {
                    type enumeration {
                        enum json;
                    }
                }                  //json
            }
            container show_ipv6_nhrp_shortcut {
                leaf json {
                    type enumeration {
                        enum json;
                    }
                }                  //json
            }
            container show_ipv6_nhrp_opennhrp {
                leaf json {
                    type enumeration {
                        enum json;
                    }
                }                  //json
            }
            container show_ipv6_route_summary {
                leaf table {
                    type enumeration {
                        enum table;
                    }
                }                  //table
                leaf THE_TABLE_NUMBER {
                    type int32;
                }                  //(1-4294967295)
                leaf prefix {
                    type enumeration {
                        enum prefix;
                    }
                }                  //prefix
                leaf prefix_json {
                    type enumeration {
                        enum prefix_json;
                    }
                }                  //json
                leaf json {
                    type enumeration {
                        enum json;
                    }
                }                  //json
            }
            container show_ipv6_mroute_vrf {
                leaf THE_VRF_NAME {
                    type string;
                }                  //NAME
                leaf THE_SOURCE_OR_GROUP {
                    type inet:ipv6-address;
                }                  //X:X::X:X
                leaf THE_GROUP {
                    type inet:ipv6-address;
                }                  //X:X::X:X
                leaf fill {
                    type enumeration {
                        enum fill;
                    }
                }                  //fill
                leaf fill_json {
                    type enumeration {
                        enum fill_json;
                    }
                }                  //json
                leaf json {
                    type enumeration {
                        enum json;
                    }
                }                  //json
                leaf count {
                    type enumeration {
                        enum count;
                    }
                }                  //count
                leaf count_json {
                    type enumeration {
                        enum count_json;
                    }
                }                  //json
                leaf summary {
                    type enumeration {
                        enum summary;
                    }
                }                  //summary
                leaf summary_json {
                    type enumeration {
                        enum summary_json;
                    }
                }                  //json
            }
            container show_ipv6_mroute_fill {
                leaf json {
                    type enumeration {
                        enum json;
                    }
                }                  //json
            }
            container show_ipv6_mroute_count {
                leaf json {
                    type enumeration {
                        enum json;
                    }
                }                  //json
            }
            container show_ipv6_mroute_summary {
                leaf json {
                    type enumeration {
                        enum json;
                    }
                }                  //json
            }
            container show_ipv6_multicast_vrf {
                leaf THE_VRF_NAME {
                    type string;
                }                  //NAME
                leaf all {
                    type enumeration {
                        enum all;
                    }
                }                  //all
            }
            container show_ipv6_multicast_count {
                leaf json {
                    type enumeration {
                        enum json;
                    }
                }                  //json
            }
            container show_ipv6_nd_ra-interfaces {
                leaf vrf {
                    type enumeration {
                        enum vrf;
                    }
                }                  //vrf
                leaf THE_VRF_NAME {
                    type string;
                }                  //NAME
                leaf all {
                    type enumeration {
                        enum all;
                    }
                }
            }
            container show_ipv6_nht_vrf {
                leaf THE_VRF_NAME {
                    type string;
                }                  //NAME
                leaf IP_ADDRESS {
                    type union {
                        type inet:ipv4-address;
                        type inet:ipv6-address;
                    }
                }                  //<A.B.C.D|X:X::X:X>
                leaf mrib {
                    type enumeration {
                        enum mrib;
                    }
                }                  //mrib
                leaf mrib_json {
                    type enumeration {
                        enum mrib_json;
                    }
                }                  //json
                leaf json {
                    type enumeration {
                        enum json;
                    }
                }                  //json
            }
            container show_ipv6_nht_mrib {
                leaf json {
                    type enumeration {
                        enum json;
                    }
                }                  //json
            }
            container show_ipv6_nht_route-map {
                leaf vrf {
                    type enumeration {
                        enum vrf;
                    }
                }                  //vrf
                leaf THE_VRF_NAME {
                    type string;
                }                  //NAME
                leaf all {
                    type enumeration {
                        enum all;
                    }
                }
                leaf json {
                    type enumeration {
                        enum json;
                    }
                }                  //json
            }
            container show_ipv6_import-check_vrf {
                leaf THE_VRF_NAME {
                    type string;
                }                  //NAME
                leaf IP_ADDRESS {
                    type union {
                        type inet:ipv4-address;
                        type inet:ipv6-address;
                    }
                }                  //<A.B.C.D|X:X::X:X>
                leaf mrib {
                    type enumeration {
                        enum mrib;
                    }
                }                  //mrib
                leaf mrib_json {
                    type enumeration {
                        enum mrib_json;
                    }
                }                  //json
                leaf json {
                    type enumeration {
                        enum json;
                    }
                }                  //json
            }
            container show_ipv6_import-check_mrib {
                leaf json {
                    type enumeration {
                        enum json;
                    }
                }                  //json
            }
            container show_ipv6_ospf6_border-routers {
                leaf ROUTER_ID {
                    type inet:ipv4-address;
                }                  //A.B.C.D
                leaf detail {
                    type enumeration {
                        enum detail;
                    }
                }
            }
            container show_ipv6_ospf6_database {
                leaf ANY_LINK_STATE_TYPE {
                    type string;
                }                  //*
                leaf ANY_LINK_STATE_ID {
                    type string;
                }                  //*
                leaf SPECIFY_ADVERTISING_ROUTER_AS {
                    type inet:ipv4-address;
                }                  //A.B.C.D
                leaf CHOICE_CASE {
                    type enumeration {
                        enum detail;
                        enum dump;
                        enum internal;
                    }
                }                  //<detail|dump|internal> ['Display details of LSAs', 'Dump LSAs', "Display LSA's internal information"]
                leaf json {
                    type enumeration {
                        enum json;
                    }
                }                  //json
                leaf SPECIFY_LINK_STATE_ID {
                    type inet:ipv4-address;
                }                  //A.B.C.D
                leaf self-originated {
                    type enumeration {
                        enum self-originated;
                    }
                }                  //self-originated
                leaf self-originated_json {
                    type enumeration {
                        enum self-originated_json;
                    }
                }                  //json
                leaf adv-router {
                    type enumeration {
                        enum adv-router;
                    }
                }                  //adv-router
                leaf linkstate-id {
                    type enumeration {
                        enum linkstate-id;
                    }
                }                  //linkstate-id
                leaf self-originated_linkstate-id {
                    type enumeration {
                        enum self-originated_linkstate-id;
                    }
                }                  //linkstate-id
            }
            container show_ipv6_ospf6_interface {
                leaf INTERFACE_NAME {
                    type string;
                }                  //IFNAME
                leaf prefix {
                    type enumeration {
                        enum prefix;
                    }
                }                  //prefix
                leaf OSPF6_ROUTE_ADDRESS_STR {
                    type union {
                        type inet:ipv6-address;
                        type inet:ipv6-prefix;
                    }
                }                  //<X:X::X:X|X:X::X:X/M>
                leaf ROUTE_PREFIX_MATCH_DETAIL {
                    type enumeration {
                        enum match;
                        enum detail;
                    }
                }                  //<match|detail> ['Display details of the prefixes', 'JavaScript Object Notation']
                leaf json {
                    type enumeration {
                        enum json;
                    }
                }                  //json
                leaf prefix_json {
                    type enumeration {
                        enum prefix_json;
                    }
                }                  //json
                leaf prefix_detail {
                    type enumeration {
                        enum prefix_detail;
                    }
                }                  //prefix_detail
                leaf prefix_detail_json {
                    type enumeration {
                        enum prefix_detail_json;
                    }
                }                  //json
            }
            container show_ipv6_ospf6_linkstate {
                leaf router {
                    type inet:ipv4-address;
                }                  //A.B.C.D
                leaf network {
                    type inet:ipv4-address;
                }                  //A.B.C.D
                leaf DISPLAY_NETWORK_ENTRY {
                    type inet:ipv4-address;
                }                  //A.B.C.D
                leaf detail {
                    type enumeration {
                        enum detail;
                    }
                }                  //detail
            }
            container show_ipv6_ospf6_neighbor {
                leaf SPECIFY_ROUTER-ID_AS_IPV4 {
                    type inet:ipv4-address;
                }                  //A.B.C.D
                leaf json {
                    type enumeration {
                        enum json;
                    }
                }                  //json
                leaf CHOICE_CASE {
                    type enumeration {
                        enum detail;
                        enum drchoice;
                    }
                }                  //<detail|drchoice> ['Display details', 'Display DR choices']
            }
            container show_ipv6_ospf6_redistribute {
                leaf json {
                    type enumeration {
                        enum json;
                    }
                }                  //json
            }
            container show_ipv6_ospf6_route {
                leaf ROUTE_TYPE_FILTER {
                    type enumeration {
                        enum intra-area;
                        enum inter-area;
                        enum external-1;
                        enum external-2;
                    }
                }                  //<intra-area|inter-area|external-1|external-2> ['Display Intra-Area routes', 'Display Inter-Area routes', 'Display Type-1 External routes', 'Display Type-2 External routes']
                leaf detail {
                    type enumeration {
                        enum detail;
                    }
                }                  //detail
                leaf detail_json {
                    type enumeration {
                        enum detail_json;
                    }
                }                  //json
                leaf SPECIFY_IPV6_PREFIX {
                    type inet:ipv6-prefix;
                }                  //X:X::X:X/M
                leaf match {
                    type enumeration {
                        enum match;
                    }
                }                  //match
                leaf match_json {
                    type enumeration {
                        enum match_json;
                    }
                }                  //json
                leaf longer {
                    type enumeration {
                        enum longer;
                    }
                }                  //longer
                leaf longer_json {
                    type enumeration {
                        enum longer_json;
                    }
                }                  //json
                leaf match_detail {
                    type enumeration {
                        enum match_detail;
                    }
                }                  //match_detail
                leaf match_detail_json {
                    type enumeration {
                        enum match_detail_json;
                    }
                }                  //json
                leaf SPECIFY_IPV6_ADDRESS {
                    type union {
                        type inet:ipv6-address;
                        type inet:ipv6-prefix;
                    }
                }                  //<X:X::X:X|X:X::X:X/M>
                leaf ROUTE_FILTER_DETAIL_SUMMARY {
                    type enumeration {
                        enum intra-area;
                        enum inter-area;
                        enum external-1;
                        enum external-2;
                        enum detail;
                        enum summary;
                    }
                }                  //<intra-area|inter-area|external-1|external-2|detail|summary> ['Display Intra-Area routes', 'Display Inter-Area routes', 'Display Type-1 External routes', 'Display Type-2 External routes', 'Specify IPv6 address', 'Specify IPv6 prefix', 'Detailed information', 'Summary of route table']
                leaf json {
                    type enumeration {
                        enum json;
                    }
                }                  //json
            }
            container show_ipv6_ospf6_simulate {
                leaf spf-tree {
                    type enumeration {
                        enum spf-tree;
                    }
                }                  //spf-tree
                leaf SPECIFY_ROOT_ROUTER-ID_TO {
                    type inet:ipv4-address;
                }                  //A.B.C.D
                leaf area {
                    type enumeration {
                        enum area;
                    }
                }                  //area
                leaf AREA_ID {
                    type inet:ipv4-address;
                }                  //A.B.C.D
            }
            container show_ipv6_ospf6_summary-address {
                leaf json {
                    type enumeration {
                        enum json;
                    }
                }                  //json
            }
            container show_ipv6_ospf6_vrfs {
                leaf json {
                    type enumeration {
                        enum json;
                    }
                }                  //json
            }
            container show_ipv6_ospf6_zebra {
                leaf json {
                    type enumeration {
                        enum json;
                    }
                }                  //json
            }
            container show_ipv6_pim_vrf {
                leaf THE_VRF_NAME {
                    type string;
                }                  //NAME
                leaf channel {
                    type enumeration {
                        enum channel;
                    }
                }                  //channel
                leaf channel_json {
                    type enumeration {
                        enum channel_json;
                    }
                }                  //json
                leaf interface {
                    type enumeration {
                        enum interface;
                    }
                }                  //interface
                leaf interface_json {
                    type enumeration {
                        enum interface_json;
                    }
                }                  //json
                leaf join {
                    type enumeration {
                        enum join;
                    }
                }                  //join
                leaf join_json {
                    type enumeration {
                        enum join_json;
                    }
                }                  //json
                leaf jp-agg {
                    type enumeration {
                        enum jp-agg;
                    }
                }                  //jp-agg
                leaf local-membership {
                    type enumeration {
                        enum local-membership;
                    }
                }                  //local-membership
                leaf local-membership_json {
                    type enumeration {
                        enum local-membership_json;
                    }
                }                  //json
                leaf neighbor {
                    type enumeration {
                        enum neighbor;
                    }
                }                  //neighbor
                leaf neighbor_json {
                    type enumeration {
                        enum neighbor_json;
                    }
                }                  //json
                leaf nexthop {
                    type enumeration {
                        enum nexthop;
                    }
                }                  //nexthop
                leaf nexthop_json {
                    type enumeration {
                        enum nexthop_json;
                    }
                }                  //json
                leaf nexthop-lookup {
                    type enumeration {
                        enum nexthop-lookup;
                    }
                }                  //nexthop-lookup
                leaf SOURCERP_ADDRESS {
                    type inet:ipv6-address;
                }                  //X:X::X:X
                leaf MULTICAST_GROUP_ADDRESS {
                    type inet:ipv6-address;
                }                  //X:X::X:X
                leaf rp-info {
                    type enumeration {
                        enum rp-info;
                    }
                }                  //rp-info
                leaf rp-info_json {
                    type enumeration {
                        enum rp-info_json;
                    }
                }                  //json
                leaf rpf {
                    type enumeration {
                        enum rpf;
                    }
                }                  //rpf
                leaf rpf_json {
                    type enumeration {
                        enum rpf_json;
                    }
                }                  //json
                leaf secondary {
                    type enumeration {
                        enum secondary;
                    }
                }                  //secondary
                leaf state {
                    type enumeration {
                        enum state;
                    }
                }                  //state
                leaf state_json {
                    type enumeration {
                        enum state_json;
                    }
                }                  //json
                leaf statistics {
                    type enumeration {
                        enum statistics;
                    }
                }                  //statistics
                leaf statistics_interface {
                    type enumeration {
                        enum statistics_interface;
                    }
                }                  //interface
                leaf PIM_INTERFACE {
                    type string;
                }                  //WORD
                leaf json {
                    type enumeration {
                        enum json;
                    }
                }                  //json
                leaf statistics_json {
                    type enumeration {
                        enum statistics_json;
                    }
                }                  //json
                leaf upstream {
                    type enumeration {
                        enum upstream;
                    }
                }                  //upstream
                leaf upstream_json {
                    type enumeration {
                        enum upstream_json;
                    }
                }                  //json
                leaf upstream-join-desired {
                    type enumeration {
                        enum upstream-join-desired;
                    }
                }                  //upstream-join-desired
                leaf upstream-join-desired_json {
                    type enumeration {
                        enum upstream-join-desired_json;
                    }
                }                  //json
                leaf upstream-rpf {
                    type enumeration {
                        enum upstream-rpf;
                    }
                }                  //upstream-rpf
                leaf upstream-rpf_json {
                    type enumeration {
                        enum upstream-rpf_json;
                    }
                }                  //json
                leaf interface_detail {
                    type enumeration {
                        enum interface_detail;
                    }
                }                  //interface_detail
                leaf interface_detail_json {
                    type enumeration {
                        enum interface_detail_json;
                    }
                }                  //json
                leaf interface_traffic {
                    type enumeration {
                        enum interface_traffic;
                    }
                }                  //interface_traffic
                leaf interface_traffic_json {
                    type enumeration {
                        enum interface_traffic_json;
                    }
                }                  //json
                leaf neighbor_detail {
                    type enumeration {
                        enum neighbor_detail;
                    }
                }                  //neighbor_detail
                leaf neighbor_detail_json {
                    type enumeration {
                        enum neighbor_detail_json;
                    }
                }                  //json
            }
            container show_ipv6_pim_channel {
                leaf json {
                    type enumeration {
                        enum json;
                    }
                }                  //json
            }
            container show_ipv6_pim_interface {
                leaf INTERFACE_NAME {
                    type string;
                }                  //WORD
                leaf json {
                    type enumeration {
                        enum json;
                    }
                }                  //json
            }
            container show_ipv6_pim_join {
                leaf THE_SOURCE_OR_GROUP {
                    type inet:ipv6-address;
                }                  //X:X::X:X
                leaf THE_GROUP {
                    type inet:ipv6-address;
                }                  //X:X::X:X
                leaf json {
                    type enumeration {
                        enum json;
                    }
                }                  //json
            }
            container show_ipv6_pim_local-membership {
                leaf json {
                    type enumeration {
                        enum json;
                    }
                }                  //json
            }
            container show_ipv6_pim_neighbor {
                leaf NAME_OF_INTERFACE_OR {
                    type string;
                }                  //WORD
                leaf json {
                    type enumeration {
                        enum json;
                    }
                }                  //json
            }
            container show_ipv6_pim_nexthop {
                leaf json {
                    type enumeration {
                        enum json;
                    }
                }                  //json
            }
            container show_ipv6_pim_rp-info {
                leaf MULTICAST_GROUP_RANGE {
                    type inet:ipv6-prefix;
                }                  //X:X::X:X/M
                leaf json {
                    type enumeration {
                        enum json;
                    }
                }                  //json
            }
            container show_ipv6_pim_rpf {
                leaf json {
                    type enumeration {
                        enum json;
                    }
                }                  //json
            }
            container show_ipv6_pim_state {
                leaf UNICAST_OR_MULTICAST_ADDRESS {
                    type inet:ipv6-address;
                }                  //X:X::X:X
                leaf MULTICAST_ADDRESS {
                    type inet:ipv6-address;
                }                  //X:X::X:X
                leaf json {
                    type enumeration {
                        enum json;
                    }
                }                  //json
            }
            container show_ipv6_pim_statistics {
                leaf interface {
                    type enumeration {
                        enum interface;
                    }
                }                  //interface
                leaf PIM_INTERFACE {
                    type string;
                }                  //WORD
                leaf json {
                    type enumeration {
                        enum json;
                    }
                }                  //json
            }
            container show_ipv6_pim_upstream {
                leaf THE_SOURCE_OR_GROUP {
                    type inet:ipv6-address;
                }                  //X:X::X:X
                leaf THE_GROUP {
                    type inet:ipv6-address;
                }                  //X:X::X:X
                leaf json {
                    type enumeration {
                        enum json;
                    }
                }                  //json
            }
            container show_ipv6_pim_upstream-join-desired {
                leaf json {
                    type enumeration {
                        enum json;
                    }
                }                  //json
            }
            container show_ipv6_pim_upstream-rpf {
                leaf json {
                    type enumeration {
                        enum json;
                    }
                }                  //json
            }
            container show_ipv6_pim_bsm-database {
                leaf vrf {
                    type enumeration {
                        enum vrf;
                    }
                }                  //vrf
                leaf THE_VRF_NAME {
                    type string;
                }                  //NAME
                leaf json {
                    type enumeration {
                        enum json;
                    }
                }                  //json
            }
            container show_ipv6_pim_bsr {
                leaf vrf {
                    type enumeration {
                        enum vrf;
                    }
                }                  //vrf
                leaf THE_VRF_NAME {
                    type string;
                }                  //NAME
                leaf json {
                    type enumeration {
                        enum json;
                    }
                }                  //json
            }
            container show_ipv6_pim_bsrp-info {
                leaf vrf {
                    type enumeration {
                        enum vrf;
                    }
                }                  //vrf
                leaf THE_VRF_NAME {
                    type string;
                }                  //NAME
                leaf json {
                    type enumeration {
                        enum json;
                    }
                }                  //json
            }
            container show_bgp_all_cidr-only {
                leaf wide {
                    type enumeration {
                        enum wide;
                    }
                }                  //wide
            }
            container show_bgp_all_dampening {
                leaf CHOICE_CASE {
                    type enumeration {
                        enum flap-statistics;
                        enum dampened-paths;
                    }
                }                  //<flap-statistics|dampened-paths> ['Display flap statistics of routes', 'Display paths suppressed due to dampening']
                leaf json {
                    type enumeration {
                        enum json;
                    }
                }                  //json
                leaf json_detail {
                    type enumeration {
                        enum json_detail;
                    }
                }                  //detail
                leaf wide {
                    type enumeration {
                        enum wide;
                    }
                }                  //wide
            }
            container show_bgp_all_community {
                leaf COMMUNITY_NUMBER {
                    type string;
                }                  //AA:NN
                leaf exact-match {
                    type enumeration {
                        enum exact-match;
                    }
                }                  //exact-match
                leaf exact-match_wide {
                    type enumeration {
                        enum exact-match_wide;
                    }
                }                  //wide
                leaf json {
                    type enumeration {
                        enum json;
                    }
                }                  //json
                leaf json_detail {
                    type enumeration {
                        enum json_detail;
                    }
                }                  //detail
                leaf wide {
                    type enumeration {
                        enum wide;
                    }
                }                  //wide
                leaf exact-match_json {
                    type enumeration {
                        enum exact-match_json;
                    }
                }                  //exact-match_json
                leaf exact-match_json_detail {
                    type enumeration {
                        enum exact-match_json_detail;
                    }
                }                  //detail
            }
            container show_bgp_all_detail-routes {
                leaf wide {
                    type enumeration {
                        enum wide;
                    }
                }                  //wide
            }
            container show_bgp_all_json {
                leaf detail {
                    type enumeration {
                        enum detail;
                    }
                }                  //detail
            }
            container show_bgp_all_summary {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_bgp_cidr-only_json {
                leaf detail {
                    type enumeration {
                        enum detail;
                    }
                }                  //detail
            }
            container show_bgp_dampening_parameters {
                leaf json {
                    type enumeration {
                        enum json;
                    }
                }                  //json
            }
            container show_bgp_community_local-AS {
                leaf wide {
                    type enumeration {
                        enum wide;
                    }
                }                  //wide
            }
            container show_bgp_community_no-advertise {
                leaf wide {
                    type enumeration {
                        enum wide;
                    }
                }                  //wide
            }
            container show_bgp_community_no-export {
                leaf wide {
                    type enumeration {
                        enum wide;
                    }
                }                  //wide
            }
            container show_bgp_community_graceful-shutdown {
                leaf wide {
                    type enumeration {
                        enum wide;
                    }
                }                  //wide
            }
            container show_bgp_community_no-peer {
                leaf wide {
                    type enumeration {
                        enum wide;
                    }
                }                  //wide
            }
            container show_bgp_community_blackhole {
                leaf wide {
                    type enumeration {
                        enum wide;
                    }
                }                  //wide
            }
            container show_bgp_community_llgr-stale {
                leaf wide {
                    type enumeration {
                        enum wide;
                    }
                }                  //wide
            }
            container show_bgp_community_no-llgr {
                leaf wide {
                    type enumeration {
                        enum wide;
                    }
                }                  //wide
            }
            container show_bgp_community_accept-own {
                leaf wide {
                    type enumeration {
                        enum wide;
                    }
                }                  //wide
            }
            container show_bgp_community_accept-own-nexthop {
                leaf wide {
                    type enumeration {
                        enum wide;
                    }
                }                  //wide
            }
            container show_bgp_community_route-filter-v6 {
                leaf wide {
                    type enumeration {
                        enum wide;
                    }
                }                  //wide
            }
            container show_bgp_community_route-filter-v4 {
                leaf wide {
                    type enumeration {
                        enum wide;
                    }
                }                  //wide
            }
            container show_bgp_community_route-filter-translated-v6 {
                leaf wide {
                    type enumeration {
                        enum wide;
                    }
                }                  //wide
            }
            container show_bgp_community_route-filter-translated-v4 {
                leaf wide {
                    type enumeration {
                        enum wide;
                    }
                }                  //wide
            }
            container show_bgp_community_exact-match {
                leaf wide {
                    type enumeration {
                        enum wide;
                    }
                }                  //wide
            }
            container show_bgp_community_json {
                leaf detail {
                    type enumeration {
                        enum detail;
                    }
                }                  //detail
            }
            container show_bgp_detail-routes_json {
                leaf detail {
                    type enumeration {
                        enum detail;
                    }
                }                  //detail
            }
            container show_bgp_neighbors_graceful-restart {
                leaf json {
                    type enumeration {
                        enum json;
                    }
                }                  //json
            }
            container show_bgp_summary_established {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_bgp_summary_failed {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_bgp_summary_terse {
                leaf json {
                    type enumeration {
                        enum json;
                    }
                }                  //json
            }
            container show_bgp_summary_wide {
                leaf json {
                    type enumeration {
                        enum json;
                    }
                }                  //json
            }
            container show_bgp_l2vpn_evpn {
                leaf json {
                    type enumeration {
                        enum json;
                    }
                }                  //json
                leaf neighbors {
                    type enumeration {
                        enum neighbors;
                    }
                }                  //neighbors
                leaf IP_ADDRESS {
                    type union {
                        type inet:ipv4-address;
                        type inet:ipv6-address;
                        type string;
                    }
                }                  //<A.B.C.D|X:X::X:X|WORD>
                leaf advertised-routes {
                    type enumeration {
                        enum advertised-routes;
                    }
                }                  //advertised-routes
                leaf advertised-routes_json {
                    type enumeration {
                        enum advertised-routes_json;
                    }
                }                  //json
                leaf routes {
                    type enumeration {
                        enum routes;
                    }
                }                  //routes
                leaf routes_json {
                    type enumeration {
                        enum routes_json;
                    }
                }                  //json
                leaf rd {
                    type enumeration {
                        enum rd;
                    }
                }                  //rd
                leaf BGP_IDENTIFIER {
                    type string;
                }                  //ASN:NN_OR_IP-ADDRESS:NN
                leaf all {
                    type enumeration {
                        enum all;
                    }
                }
                leaf overlay {
                    type enumeration {
                        enum overlay;
                    }
                }                  //overlay
                leaf tags {
                    type enumeration {
                        enum tags;
                    }
                }                  //tags
                leaf update-groups {
                    type enumeration {
                        enum update-groups;
                    }
                }                  //update-groups
                leaf IPV4_PREFIX {
                    type union {
                        type inet:ipv4-address;
                        type inet:ipv4-prefix;
                        type inet:ipv6-address;
                        type inet:ipv6-prefix;
                    }
                }                  //<A.B.C.D|A.B.C.D/M|X:X::X:X|X:X::X:X/M>
                leaf community {
                    type string;
                }                  //AA:NN
                leaf large-community {
                    type string;
                }                  //AA:BB:CC
                leaf exact-match {
                    type enumeration {
                        enum exact-match;
                    }
                }                  //exact-match
                leaf exact-match_json {
                    type enumeration {
                        enum exact-match_json;
                    }
                }                  //json
                leaf vni-svi-hash {
                    type enumeration {
                        enum vni-svi-hash;
                    }
                }                  //vni-svi-hash
            }
            container show_bgp_vrf_all {
                leaf REDISTRIBUTE_IP {
                    type enumeration {
                        enum ipv4;
                        enum ipv6;
                    }
                }                  //<ipv4|ipv6> ['Address Family', 'Address Family']
                leaf CHOICE_CASE {
                    type enumeration {
                        enum unicast;
                        enum multicast;
                        enum vpn;
                        enum labeled-unicast;
                        enum flowspec;
                    }
                }                  //<unicast|multicast|vpn|labeled-unicast|flowspec> ['Address Family modifier', 'Address Family modifier', 'Address Family modifier', 'Address Family modifier', 'Address Family modifier']
                leaf json {
                    type enumeration {
                        enum json;
                    }
                }                  //json
                leaf wide {
                    type enumeration {
                        enum wide;
                    }
                }                  //wide
            }
            container show_bgp_view_all {
                leaf REDISTRIBUTE_IP {
                    type enumeration {
                        enum ipv4;
                        enum ipv6;
                    }
                }                  //<ipv4|ipv6> ['Address Family', 'Address Family']
                leaf CHOICE_CASE {
                    type enumeration {
                        enum unicast;
                        enum multicast;
                        enum vpn;
                        enum labeled-unicast;
                        enum flowspec;
                    }
                }                  //<unicast|multicast|vpn|labeled-unicast|flowspec> ['Address Family modifier', 'Address Family modifier', 'Address Family modifier', 'Address Family modifier', 'Address Family modifier']
                leaf json {
                    type enumeration {
                        enum json;
                    }
                }                  //json
                leaf wide {
                    type enumeration {
                        enum wide;
                    }
                }                  //wide
            }
            container show_bgp_labelpool_chunks {
                leaf json {
                    type enumeration {
                        enum json;
                    }
                }                  //json
            }
            container show_bgp_labelpool_inuse {
                leaf json {
                    type enumeration {
                        enum json;
                    }
                }                  //json
            }
            container show_bgp_labelpool_ledger {
                leaf json {
                    type enumeration {
                        enum json;
                    }
                }                  //json
            }
            container show_bgp_labelpool_requests {
                leaf json {
                    type enumeration {
                        enum json;
                    }
                }                  //json
            }
            container show_bgp_labelpool_summary {
                leaf json {
                    type enumeration {
                        enum json;
                    }
                }                  //json
            }
            container show_bgp_vni_all {
                leaf vtep {
                    type enumeration {
                        enum vtep;
                    }
                }                  //vtep
                leaf REMOTE_VTEP_IP_ADDRESS {
                    type inet:ipv4-address;
                }                  //A.B.C.D
                leaf detail {
                    type enumeration {
                        enum detail;
                    }
                }                  //detail
                leaf detail_json {
                    type enumeration {
                        enum detail_json;
                    }
                }                  //json
                leaf json {
                    type enumeration {
                        enum json;
                    }
                }                  //json
            }
            container show_configuration_running_with-defaults {
                leaf DAEMONS_LIST {
                    type enumeration {
                        enum babeld;
                        enum bgpd;
                        enum fabricd;
                        enum ldpd;
                        enum ospfd;
                        enum pbrd;
                        enum pimd;
                        enum ripngd;
                        enum vrrpd;
                        enum bfdd;
                        enum eigrpd;
                        enum isisd;
                        enum nhrpd;
                        enum ospf6d;
                        enum pathd;
                        enum pim6d;
                        enum ripd;
                        enum staticd;
                        enum zebra;
                    }
                }                  //<babeld|bgpd|fabricd|ldpd|ospfd|pbrd|pimd|ripngd|vrrpd|bfdd|eigrpd|isisd|nhrpd|ospf6d|pathd|pim6d|ripd|staticd|zebra> ['For the babeld daemon', 'For the bgpd daemon', 'For the fabricd daemon', 'For the ldpd daemon', 'For the ospfd daemon', 'For the pbrd daemon', 'For the pimd daemon', 'For the ripngd daemon', 'For the vrrpd daemon', 'For the bfdd daemon', 'For the eigrpd daemon', 'For the isisd daemon', 'For the nhrpd daemon', 'For the ospf6d daemon', 'For the pathd daemon', 'For the pim6d daemom', 'For the ripd daemon', 'For the staticd daemon', 'For the zebra daemon']
            }
            container show_evpn_access-vlan_detail {
                leaf json {
                    type enumeration {
                        enum json;
                    }
                }                  //json
            }
            container show_evpn_arp-cache_vni {
                leaf VNI_NUMBER {
                    type int32;
                }                  //(1-16777215)
                leaf json {
                    type enumeration {
                        enum json;
                    }
                }                  //json
                leaf duplicate {
                    type enumeration {
                        enum duplicate;
                    }
                }                  //duplicate
                leaf duplicate_json {
                    type enumeration {
                        enum duplicate_json;
                    }
                }                  //json
                leaf ip {
                    type enumeration {
                        enum ip;
                    }
                }                  //ip
                leaf NEIGHBOR_ADDRESS {
                    type string;
                }                  //WORD
                leaf vtep {
                    type enumeration {
                        enum vtep;
                    }
                }                  //vtep
                leaf REMOTE_VTEP_IP_ADDRESS {
                    type inet:ipv4-address;
                }                  //A.B.C.D
            }
            container show_evpn_es_detail {
                leaf json {
                    type enumeration {
                        enum json;
                    }
                }                  //json
            }
            container show_evpn_es-evi_detail {
                leaf json {
                    type enumeration {
                        enum json;
                    }
                }                  //json
            }
            container show_evpn_mac_vni {
                leaf VNI_NUMBER {
                    type int32;
                }                  //(1-16777215)
                leaf json {
                    type enumeration {
                        enum json;
                    }
                }                  //json
                leaf detail {
                    type enumeration {
                        enum detail;
                    }
                }                  //detail
                leaf detail_json {
                    type enumeration {
                        enum detail_json;
                    }
                }                  //json
                leaf duplicate {
                    type enumeration {
                        enum duplicate;
                    }
                }                  //duplicate
                leaf duplicate_json {
                    type enumeration {
                        enum duplicate_json;
                    }
                }                  //json
                leaf mac {
                    type enumeration {
                        enum mac;
                    }
                }                  //mac
                leaf MAC_ADDRESS_ {
                    type string;
                }                  //WORD
                leaf vtep {
                    type enumeration {
                        enum vtep;
                    }
                }                  //vtep
                leaf REMOTE_VTEP_IP_ADDRESS {
                    type inet:ipv4-address;
                }                  //A.B.C.D
            }
            container show_evpn_next-hops_vni {
                leaf VNI_NUMBER {
                    type int32;
                }                  //(1-16777215)
                leaf json {
                    type enumeration {
                        enum json;
                    }
                }                  //json
                leaf ip {
                    type enumeration {
                        enum ip;
                    }
                }                  //ip
                leaf HOST_ADDRESS {
                    type string;
                }                  //WORD
            }
            container show_evpn_rmac_vni {
                leaf VNI_NUMBER {
                    type int32;
                }                  //(1-16777215)
                leaf json {
                    type enumeration {
                        enum json;
                    }
                }                  //json
                leaf mac {
                    type enumeration {
                        enum mac;
                    }
                }                  //mac
                leaf MAC-ADDRESS_ {
                    type string;
                }                  //WORD
            }
            container show_evpn_vni_detail {
                leaf json {
                    type enumeration {
                        enum json;
                    }
                }                  //json
            }
            container show_interface_vrf_all {
                leaf json {
                    type enumeration {
                        enum json;
                    }
                }                  //json
            }
            container show_interface_description_vrf {
                leaf all {
                    type enumeration {
                        enum all;
                    }
                }                  //all
                leaf THE_VRF_NAME {
                    type string;
                }                  //NAME
            }
            container show_isis_database_detail {
                leaf LSP_ID {
                    type string;
                }                  //WORD
                leaf json {
                    type enumeration {
                        enum json;
                    }
                }                  //json
            }
            container show_isis_interface_detail {
                leaf json {
                    type enumeration {
                        enum json;
                    }
                }                  //json
            }
            container show_isis_mpls-te_database {
                leaf detail {
                    type enumeration {
                        enum detail;
                    }
                }                  //detail
                leaf json {
                    type enumeration {
                        enum json;
                    }
                }                  //json
            }
            container show_isis_mpls-te_interface {
                leaf INTERFACE_NAME {
                    type string;
                }                  //INTERFACE
            }
            container show_isis_neighbor_detail {
                leaf json {
                    type enumeration {
                        enum json;
                    }
                }                  //json
            }
            container show_isis_mpls_ldp-sync {
                leaf interface {
                    type enumeration {
                        enum interface;
                    }
                }                  //interface
                leaf INTERFACE_NAME {
                    type string;
                }                  //INTERFACE
                leaf all {
                    type enumeration {
                        enum all;
                    }
                }
            }
            container show_segment-routing_srv6_locator {
                leaf LOCATOR_NAME {
                    type string;
                }                  //NAME
                leaf detail {
                    type enumeration {
                        enum detail;
                    }
                }                  //detail
                leaf detail_json {
                    type enumeration {
                        enum detail_json;
                    }
                }                  //json
                leaf json {
                    type enumeration {
                        enum json;
                    }
                }                  //json
            }
            container show_zebra_dplane_providers {
                leaf detailed {
                    type enumeration {
                        enum detailed;
                    }
                }                  //detailed
            }
            container show_zebra_router_table {
                leaf summary {
                    type enumeration {
                        enum summary;
                    }
                }                  //summary
            }
            container show_bfd_peers_brief {
                leaf json {
                    type enumeration {
                        enum json;
                    }
                }                  //json
            }
            container show_bfd_peers_counters {
                leaf json {
                    type enumeration {
                        enum json;
                    }
                }                  //json
            }
            container show_bfd_peer_counters {
                leaf json {
                    type enumeration {
                        enum json;
                    }
                }                  //json
            }
            container show_bfd_static_route {
                leaf json {
                    type enumeration {
                        enum json;
                    }
                }                  //json
            }
            container show_sharp_segment-routing_srv6 {
                leaf json {
                    type enumeration {
                        enum json;
                    }
                }                  //json
            }
            container show_sharp_ted_vertex {
                leaf MPLS-TE_ROUTER_ID {
                    type inet:ipv4-address;
                }                  //A.B.C.D
                leaf verbose {
                    type enumeration {
                        enum verbose;
                    }
                }                  //verbose
                leaf json {
                    type enumeration {
                        enum json;
                    }
                }                  //json
            }
            container show_sharp_ted_edge {
                leaf MPLS-TE_EDGE_ID {
                    type inet:ipv4-address;
                }                  //A.B.C.D
                leaf verbose {
                    type enumeration {
                        enum verbose;
                    }
                }                  //verbose
                leaf json {
                    type enumeration {
                        enum json;
                    }
                }                  //json
            }
            container show_sharp_ted_subnet {
                leaf IPV4_PREFIX {
                    type inet:ipv4-prefix;
                }                  //A.B.C.D/M
                leaf verbose {
                    type enumeration {
                        enum verbose;
                    }
                }                  //verbose
                leaf json {
                    type enumeration {
                        enum json;
                    }
                }                  //json
            }
            container debug_bgp_lptest_release {
                leaf test {
                    type enumeration {
                        enum test;
                    }
                }                  //test
                leaf TEST_NUMBER {
                    type string;
                }                  //GENERATION
                leaf every {
                    type enumeration {
                        enum every;
                    }
                }                  //every
                leaf LABEL_FRACTION_DENOMINATOR {
                    type int32;
                }                  //(1-5)
            }
            container debug_bgp_updates_prefix {
                leaf IPV4_PREFIX {
                    type union {
                        type inet:ipv4-prefix;
                        type inet:ipv6-prefix;
                    }
                }                  //<A.B.C.D/M|X:X::X:X/M>
            }
            container debug_zebra_dplane_dpdk {
                leaf detailed {
                    type enumeration {
                        enum detailed;
                    }
                }                  //detailed
            }
            container debug_zebra_kernel_msgdump {
                leaf CHOICE_CASE {
                    type enumeration {
                        enum recv;
                        enum send;
                    }
                }                  //<recv|send> ['Dump raw netlink messages received', 'Dump raw netlink messages sent']
            }
            container debug_rfapi-dev_query_done {
                leaf vn {
                    type enumeration {
                        enum vn;
                    }
                }                  //vn
                leaf IP_ADDRESS {
                    type union {
                        type inet:ipv4-address;
                        type inet:ipv6-address;
                    }
                }                  //<A.B.C.D|X:X::X:X>
                leaf un {
                    type enumeration {
                        enum un;
                    }
                }                  //un
                leaf target {
                    type enumeration {
                        enum target;
                    }
                }                  //target
            }
            container debug_rfapi-dev_show_import {
                leaf vn {
                    type enumeration {
                        enum vn;
                    }
                }                  //vn
                leaf IP_ADDRESS {
                    type union {
                        type inet:ipv4-address;
                        type inet:ipv6-address;
                    }
                }                  //<A.B.C.D|X:X::X:X>
                leaf un {
                    type enumeration {
                        enum un;
                    }
                }                  //un
            }
            container debug_rfapi-dev_show_nves {
                leaf OVERLAY_ADDRESS_MODE {
                    type enumeration {
                        enum vn;
                        enum un;
                    }
                }                  //<vn|un> ['Specify virtual network', 'Specify underlay network interface']
                leaf IP_ADDRESS {
                    type union {
                        type inet:ipv4-address;
                        type inet:ipv6-address;
                    }
                }                  //<A.B.C.D|X:X::X:X>
            }
            container clear_ip_bgp_dampening {
                leaf NETWORK_TO_CLEAR_DAMPING {
                    type inet:ipv4-address;
                }                  //A.B.C.D
                leaf NETWORK_MASK {
                    type inet:ipv4-address;
                }                  //A.B.C.D
                leaf IPV4_PREFIX {
                    type inet:ipv4-prefix;
                }                  //A.B.C.D/M
            }
            container clear_ip_ospf_neighbor {
                leaf NEIGHBOR_ID {
                    type inet:ipv4-address;
                }                  //A.B.C.D
            }
            container clear_ip_ospf_interface {
                leaf INTERFACE_NAME {
                    type string;
                }                  //IFNAME
            }
            container clear_ip_pim_interface {
                leaf traffic {
                    type enumeration {
                        enum traffic;
                    }
                }                  //traffic
            }
            container clear_ip_pim_statistics {
                leaf vrf {
                    type enumeration {
                        enum vrf;
                    }
                }                  //vrf
                leaf RESET_PIM_STATISTICS {
                    type string;
                }                  //NAME
            }
            container clear_ipv6_ospf6_vrf {
                leaf THE_VRF_NAME {
                    type string;
                }                  //NAME
                leaf interface {
                    type enumeration {
                        enum interface;
                    }
                }                  //interface
                leaf auth-counters_interface {
                    type enumeration {
                        enum auth-counters_interface;
                    }
                }                  //auth-counters_interface
            }
            container clear_ipv6_ospf6_interface {
                leaf INTERFACE_NAME {
                    type string;
                }                  //IFNAME
            }
            container clear_ipv6_ospf6_process {
                leaf vrf {
                    type enumeration {
                        enum vrf;
                    }
                }                  //vrf
                leaf THE_VRF_NAME {
                    type string;
                }                  //NAME
            }
            container clear_ipv6_pim_interface {
                leaf traffic {
                    type enumeration {
                        enum traffic;
                    }
                }                  //traffic
            }
            container clear_ipv6_pim_statistics {
                leaf vrf {
                    type enumeration {
                        enum vrf;
                    }
                }                  //vrf
                leaf RESET_PIM_STATISTICS {
                    type string;
                }                  //NAME
            }
            container clear_evpn_dup-addr_vni {
                leaf all {
                    type enumeration {
                        enum all;
                    }
                }                  //all
                leaf ALL_VNIS {
                    type int32;
                }                  //(1-16777215)
                leaf mac {
                    type enumeration {
                        enum mac;
                    }
                }                  //mac
                leaf MAC_ADDRESS_ {
                    type string;
                }                  //X:X:X:X:X:X
                leaf ip {
                    type enumeration {
                        enum ip;
                    }
                }                  //ip
                leaf IP_ADDRESS {
                    type union {
                        type inet:ipv4-address;
                        type inet:ipv6-address;
                    }
                }                  //<A.B.C.D|X:X::X:X>
            }
            container no_debug_bgp_updates_prefix {
                leaf IPV4_PREFIX {
                    type union {
                        type inet:ipv4-prefix;
                        type inet:ipv6-prefix;
                    }
                }                  //<A.B.C.D/M|X:X::X:X/M>
            }
            container no_debug_ospf6_border-routers_area-id {
                leaf SPECIFY_AREA-ID {
                    type inet:ipv4-address;
                }                  //A.B.C.D
            }
            container no_debug_ospf6_border-routers_router-id {
                leaf SPECIFY_BORDER-ROUTER_ROUTER-ID {
                    type inet:ipv4-address;
                }                  //A.B.C.D
            }
            container no_debug_zebra_dplane_dpdk {
                leaf detailed {
                    type enumeration {
                        enum detailed;
                    }
                }                  //detailed
            }
            container no_debug_zebra_kernel_msgdump {
                leaf CHOICE_CASE {
                    type enumeration {
                        enum recv;
                        enum send;
                    }
                }                  //<recv|send> ['Dump raw netlink messages received', 'Dump raw netlink messages sent']
            }
            container show_ip_route_summary_prefix {
                leaf json {
                    type enumeration {
                        enum json;
                    }
                }                  //json
            }
            container show_ip_zebra_route_dump {
                leaf vrf {
                    type enumeration {
                        enum vrf;
                    }
                }                  //vrf
                leaf THE_VRF_NAME {
                    type string;
                }                  //VRFNAME
            }
            container show_ip_bgp_all_cidr-only {
                leaf wide {
                    type enumeration {
                        enum wide;
                    }
                }                  //wide
            }
            container show_ip_bgp_all_dampening {
                leaf CHOICE_CASE {
                    type enumeration {
                        enum flap-statistics;
                        enum dampened-paths;
                    }
                }                  //<flap-statistics|dampened-paths> ['Display flap statistics of routes', 'Display paths suppressed due to dampening']
                leaf json {
                    type enumeration {
                        enum json;
                    }
                }                  //json
                leaf json_detail {
                    type enumeration {
                        enum json_detail;
                    }
                }                  //detail
                leaf wide {
                    type enumeration {
                        enum wide;
                    }
                }                  //wide
            }
            container show_ip_bgp_all_community {
                leaf COMMUNITY_NUMBER {
                    type string;
                }                  //AA:NN
                leaf exact-match {
                    type enumeration {
                        enum exact-match;
                    }
                }                  //exact-match
                leaf exact-match_wide {
                    type enumeration {
                        enum exact-match_wide;
                    }
                }                  //wide
                leaf json {
                    type enumeration {
                        enum json;
                    }
                }                  //json
                leaf json_detail {
                    type enumeration {
                        enum json_detail;
                    }
                }                  //detail
                leaf wide {
                    type enumeration {
                        enum wide;
                    }
                }                  //wide
                leaf exact-match_json {
                    type enumeration {
                        enum exact-match_json;
                    }
                }                  //exact-match_json
                leaf exact-match_json_detail {
                    type enumeration {
                        enum exact-match_json_detail;
                    }
                }                  //detail
            }
            container show_ip_bgp_all_detail-routes {
                leaf wide {
                    type enumeration {
                        enum wide;
                    }
                }                  //wide
            }
            container show_ip_bgp_all_json {
                leaf detail {
                    type enumeration {
                        enum detail;
                    }
                }                  //detail
            }
            container show_ip_bgp_all_summary {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_ip_bgp_cidr-only_json {
                leaf detail {
                    type enumeration {
                        enum detail;
                    }
                }                  //detail
            }
            container show_ip_bgp_dampening_parameters {
                leaf json {
                    type enumeration {
                        enum json;
                    }
                }                  //json
            }
            container show_ip_bgp_community_local-AS {
                leaf wide {
                    type enumeration {
                        enum wide;
                    }
                }                  //wide
            }
            container show_ip_bgp_community_no-advertise {
                leaf wide {
                    type enumeration {
                        enum wide;
                    }
                }                  //wide
            }
            container show_ip_bgp_community_no-export {
                leaf wide {
                    type enumeration {
                        enum wide;
                    }
                }                  //wide
            }
            container show_ip_bgp_community_graceful-shutdown {
                leaf wide {
                    type enumeration {
                        enum wide;
                    }
                }                  //wide
            }
            container show_ip_bgp_community_no-peer {
                leaf wide {
                    type enumeration {
                        enum wide;
                    }
                }                  //wide
            }
            container show_ip_bgp_community_blackhole {
                leaf wide {
                    type enumeration {
                        enum wide;
                    }
                }                  //wide
            }
            container show_ip_bgp_community_llgr-stale {
                leaf wide {
                    type enumeration {
                        enum wide;
                    }
                }                  //wide
            }
            container show_ip_bgp_community_no-llgr {
                leaf wide {
                    type enumeration {
                        enum wide;
                    }
                }                  //wide
            }
            container show_ip_bgp_community_accept-own {
                leaf wide {
                    type enumeration {
                        enum wide;
                    }
                }                  //wide
            }
            container show_ip_bgp_community_accept-own-nexthop {
                leaf wide {
                    type enumeration {
                        enum wide;
                    }
                }                  //wide
            }
            container show_ip_bgp_community_route-filter-v6 {
                leaf wide {
                    type enumeration {
                        enum wide;
                    }
                }                  //wide
            }
            container show_ip_bgp_community_route-filter-v4 {
                leaf wide {
                    type enumeration {
                        enum wide;
                    }
                }                  //wide
            }
            container show_ip_bgp_community_route-filter-translated-v6 {
                leaf wide {
                    type enumeration {
                        enum wide;
                    }
                }                  //wide
            }
            container show_ip_bgp_community_route-filter-translated-v4 {
                leaf wide {
                    type enumeration {
                        enum wide;
                    }
                }                  //wide
            }
            container show_ip_bgp_community_exact-match {
                leaf wide {
                    type enumeration {
                        enum wide;
                    }
                }                  //wide
            }
            container show_ip_bgp_community_json {
                leaf detail {
                    type enumeration {
                        enum detail;
                    }
                }                  //detail
            }
            container show_ip_bgp_detail-routes_json {
                leaf detail {
                    type enumeration {
                        enum detail;
                    }
                }                  //detail
            }
            container show_ip_bgp_summary_established {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_ip_bgp_summary_failed {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_ip_bgp_summary_terse {
                leaf json {
                    type enumeration {
                        enum json;
                    }
                }                  //json
            }
            container show_ip_bgp_summary_wide {
                leaf json {
                    type enumeration {
                        enum json;
                    }
                }                  //json
            }
            container show_ip_bgp_l2vpn_evpn {
                leaf json {
                    type enumeration {
                        enum json;
                    }
                }                  //json
                leaf neighbors {
                    type enumeration {
                        enum neighbors;
                    }
                }                  //neighbors
                leaf IP_ADDRESS {
                    type union {
                        type inet:ipv4-address;
                        type inet:ipv6-address;
                        type string;
                    }
                }                  //<A.B.C.D|X:X::X:X|WORD>
                leaf advertised-routes {
                    type enumeration {
                        enum advertised-routes;
                    }
                }                  //advertised-routes
                leaf advertised-routes_json {
                    type enumeration {
                        enum advertised-routes_json;
                    }
                }                  //json
                leaf routes {
                    type enumeration {
                        enum routes;
                    }
                }                  //routes
                leaf routes_json {
                    type enumeration {
                        enum routes_json;
                    }
                }                  //json
                leaf rd {
                    type enumeration {
                        enum rd;
                    }
                }                  //rd
                leaf BGP_IDENTIFIER {
                    type string;
                }                  //ASN:NN_OR_IP-ADDRESS:NN
                leaf all {
                    type enumeration {
                        enum all;
                    }
                }
                leaf overlay {
                    type enumeration {
                        enum overlay;
                    }
                }                  //overlay
                leaf tags {
                    type enumeration {
                        enum tags;
                    }
                }                  //tags
                leaf update-groups {
                    type enumeration {
                        enum update-groups;
                    }
                }                  //update-groups
            }
            container show_ip_igmp_interface_detail {
                leaf json {
                    type enumeration {
                        enum json;
                    }
                }                  //json
            }
            container show_ip_mroute_vrf_all {
                leaf json {
                    type enumeration {
                        enum json;
                    }
                }                  //json
            }
            container show_ip_msdp_peer_detail {
                leaf json {
                    type enumeration {
                        enum json;
                    }
                }                  //json
            }
            container show_ip_msdp_sa_detail {
                leaf json {
                    type enumeration {
                        enum json;
                    }
                }                  //json
            }
            container show_ip_multicast_count_vrf {
                leaf THE_VRF_NAME {
                    type string;
                }                  //NAME
                leaf json {
                    type enumeration {
                        enum json;
                    }
                }                  //json
            }
            container show_ip_nht_vrf_all {
                leaf json {
                    type enumeration {
                        enum json;
                    }
                }                  //json
            }
            container show_ip_import-check_vrf_all {
                leaf json {
                    type enumeration {
                        enum json;
                    }
                }                  //json
            }
            container show_ip_ospf_neighbor_all {
                leaf json {
                    type enumeration {
                        enum json;
                    }
                }                  //json
            }
            container show_ip_ospf_neighbor_detail {
                leaf json {
                    type enumeration {
                        enum json;
                    }
                }                  //json
            }
            container show_ip_ospf_database_segment-routing {
                leaf adv-router {
                    type enumeration {
                        enum adv-router;
                    }
                }                  //adv-router
                leaf ADVERTISING_SR_NODE_ID {
                    type inet:ipv4-address;
                }                  //A.B.C.D
                leaf json {
                    type enumeration {
                        enum json;
                    }
                }                  //json
            }
            container show_ip_ospf_graceful-restart_helper {
                leaf json {
                    type enumeration {
                        enum json;
                    }
                }                  //json
            }
            container show_ip_ospf_interface_traffic {
                leaf INTERFACE_NAME {
                    type string;
                }                  //INTERFACE
                leaf json {
                    type enumeration {
                        enum json;
                    }
                }                  //json
            }
            container show_ip_ospf_mpls-te_interface {
                leaf INTERFACE_NAME {
                    type string;
                }                  //INTERFACE
            }
            container show_ip_ospf_mpls-te_database {
                leaf verbose {
                    type enumeration {
                        enum verbose;
                    }
                }                  //verbose
                leaf json {
                    type enumeration {
                        enum json;
                    }
                }                  //json
            }
            container show_ip_ospf_summary-address_detail {
                leaf json {
                    type enumeration {
                        enum json;
                    }
                }                  //json
            }
            container show_ip_pim_mlag_vrf {
                leaf THE_VRF_NAME {
                    type string;
                }                  //NAME
                leaf interface {
                    type enumeration {
                        enum interface;
                    }
                }                  //interface
                leaf interface_json {
                    type enumeration {
                        enum interface_json;
                    }
                }                  //json
                leaf interface_detail {
                    type enumeration {
                        enum interface_detail;
                    }
                }                  //interface_detail
                leaf interface_detail_json {
                    type enumeration {
                        enum interface_detail_json;
                    }
                }                  //json
            }
            container show_ip_pim_mlag_interface {
                leaf INTERFACE_NAME {
                    type string;
                }                  //WORD
                leaf json {
                    type enumeration {
                        enum json;
                    }
                }                  //json
            }
            container show_ip_pim_mlag_upstream {
                leaf UNICAST_OR_MULTICAST_ADDRESS {
                    type inet:ipv4-address;
                }                  //A.B.C.D
                leaf MULTICAST_ADDRESS {
                    type inet:ipv4-address;
                }                  //A.B.C.D
                leaf json {
                    type enumeration {
                        enum json;
                    }
                }                  //json
            }
            container show_ip_pim_mlag_summary {
                leaf json {
                    type enumeration {
                        enum json;
                    }
                }                  //json
            }
            container show_ip_pim_interface_detail {
                leaf json {
                    type enumeration {
                        enum json;
                    }
                }                  //json
            }
            container show_ip_pim_interface_traffic {
                leaf INTERFACE_NAME {
                    type string;
                }                  //WORD
                leaf json {
                    type enumeration {
                        enum json;
                    }
                }                  //json
            }
            container show_ip_pim_neighbor_detail {
                leaf json {
                    type enumeration {
                        enum json;
                    }
                }                  //json
            }
            container show_ipv6_route_summary_prefix {
                leaf json {
                    type enumeration {
                        enum json;
                    }
                }                  //json
            }
            container show_ipv6_zebra_route_dump {
                leaf vrf {
                    type enumeration {
                        enum vrf;
                    }
                }                  //vrf
                leaf THE_VRF_NAME {
                    type string;
                }                  //VRFNAME
            }
            container show_ipv6_mroute_vrf_all {
                leaf json {
                    type enumeration {
                        enum json;
                    }
                }                  //json
            }
            container show_ipv6_multicast_count_vrf {
                leaf THE_VRF_NAME {
                    type string;
                }                  //NAME
                leaf json {
                    type enumeration {
                        enum json;
                    }
                }                  //json
            }
            container show_ipv6_nht_vrf_all {
                leaf json {
                    type enumeration {
                        enum json;
                    }
                }                  //json
            }
            container show_ipv6_import-check_vrf_all {
                leaf json {
                    type enumeration {
                        enum json;
                    }
                }                  //json
            }
            container show_ipv6_ospf6_database_adv-router {
                leaf ANY_LINK_STATE_ID {
                    type string;
                }                  //*
                leaf SPECIFY_ADVERTISING_ROUTER_AS {
                    type inet:ipv4-address;
                }                  //A.B.C.D
                leaf CHOICE_CASE {
                    type enumeration {
                        enum detail;
                        enum dump;
                        enum internal;
                    }
                }                  //<detail|dump|internal> ['Display details of LSAs', 'Dump LSAs', "Display LSA's internal information"]
                leaf json {
                    type enumeration {
                        enum json;
                    }
                }                  //json
                leaf linkstate-id {
                    type enumeration {
                        enum linkstate-id;
                    }
                }                  //linkstate-id
                leaf SPECIFY_LINK_STATE_ID {
                    type inet:ipv4-address;
                }                  //A.B.C.D
            }
            container show_ipv6_ospf6_database_aggr {
                leaf adv-router {
                    type enumeration {
                        enum adv-router;
                    }
                }                  //adv-router
                leaf SPECIFY_ADVERTISING_ROUTER_AS {
                    type inet:ipv4-address;
                }                  //A.B.C.D
            }
            container show_ipv6_ospf6_database_self-originated {
                leaf CHOICE_CASE {
                    type enumeration {
                        enum detail;
                        enum dump;
                        enum internal;
                    }
                }                  //<detail|dump|internal> ['Display details of LSAs', 'Dump LSAs', "Display LSA's internal information"]
                leaf json {
                    type enumeration {
                        enum json;
                    }
                }                  //json
            }
            container show_ipv6_ospf6_interface_prefix {
                leaf OSPF6_ROUTE_ADDRESS_STR {
                    type union {
                        type inet:ipv6-address;
                        type inet:ipv6-prefix;
                    }
                }                  //<X:X::X:X|X:X::X:X/M>
                leaf ROUTE_PREFIX_MATCH_DETAIL {
                    type enumeration {
                        enum match;
                        enum detail;
                    }
                }                  //<match|detail> ['Display details of the prefixes', 'JavaScript Object Notation']
                leaf json {
                    type enumeration {
                        enum json;
                    }
                }                  //json
            }
            container show_ipv6_ospf6_interface_traffic {
                leaf INTERFACE_NAME {
                    type string;
                }                  //IFNAME
                leaf json {
                    type enumeration {
                        enum json;
                    }
                }                  //json
            }
            container show_ipv6_ospf6_spf_tree {
                leaf json {
                    type enumeration {
                        enum json;
                    }
                }                  //json
            }
            container show_ipv6_ospf6_summary-address_detail {
                leaf json {
                    type enumeration {
                        enum json;
                    }
                }                  //json
            }
            container show_ipv6_pim_interface_detail {
                leaf json {
                    type enumeration {
                        enum json;
                    }
                }                  //json
            }
            container show_ipv6_pim_interface_traffic {
                leaf INTERFACE_NAME {
                    type string;
                }                  //WORD
                leaf json {
                    type enumeration {
                        enum json;
                    }
                }                  //json
            }
            container show_ipv6_pim_neighbor_detail {
                leaf json {
                    type enumeration {
                        enum json;
                    }
                }                  //json
            }
            container show_bgp_all_cidr-only_json {
                leaf detail {
                    type enumeration {
                        enum detail;
                    }
                }                  //detail
            }
            container show_bgp_all_dampening_parameters {
                leaf json {
                    type enumeration {
                        enum json;
                    }
                }                  //json
            }
            container show_bgp_all_community_local-AS {
                leaf wide {
                    type enumeration {
                        enum wide;
                    }
                }                  //wide
            }
            container show_bgp_all_community_no-advertise {
                leaf wide {
                    type enumeration {
                        enum wide;
                    }
                }                  //wide
            }
            container show_bgp_all_community_no-export {
                leaf wide {
                    type enumeration {
                        enum wide;
                    }
                }                  //wide
            }
            container show_bgp_all_community_graceful-shutdown {
                leaf wide {
                    type enumeration {
                        enum wide;
                    }
                }                  //wide
            }
            container show_bgp_all_community_no-peer {
                leaf wide {
                    type enumeration {
                        enum wide;
                    }
                }                  //wide
            }
            container show_bgp_all_community_blackhole {
                leaf wide {
                    type enumeration {
                        enum wide;
                    }
                }                  //wide
            }
            container show_bgp_all_community_llgr-stale {
                leaf wide {
                    type enumeration {
                        enum wide;
                    }
                }                  //wide
            }
            container show_bgp_all_community_no-llgr {
                leaf wide {
                    type enumeration {
                        enum wide;
                    }
                }                  //wide
            }
            container show_bgp_all_community_accept-own {
                leaf wide {
                    type enumeration {
                        enum wide;
                    }
                }                  //wide
            }
            container show_bgp_all_community_accept-own-nexthop {
                leaf wide {
                    type enumeration {
                        enum wide;
                    }
                }                  //wide
            }
            container show_bgp_all_community_route-filter-v6 {
                leaf wide {
                    type enumeration {
                        enum wide;
                    }
                }                  //wide
            }
            container show_bgp_all_community_route-filter-v4 {
                leaf wide {
                    type enumeration {
                        enum wide;
                    }
                }                  //wide
            }
            container show_bgp_all_community_route-filter-translated-v6 {
                leaf wide {
                    type enumeration {
                        enum wide;
                    }
                }                  //wide
            }
            container show_bgp_all_community_route-filter-translated-v4 {
                leaf wide {
                    type enumeration {
                        enum wide;
                    }
                }                  //wide
            }
            container show_bgp_all_community_exact-match {
                leaf wide {
                    type enumeration {
                        enum wide;
                    }
                }                  //wide
            }
            container show_bgp_all_community_json {
                leaf detail {
                    type enumeration {
                        enum detail;
                    }
                }                  //detail
            }
            container show_bgp_all_detail-routes_json {
                leaf detail {
                    type enumeration {
                        enum detail;
                    }
                }                  //detail
            }
            container show_bgp_all_summary_established {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_bgp_all_summary_failed {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_bgp_all_summary_terse {
                leaf json {
                    type enumeration {
                        enum json;
                    }
                }                  //json
            }
            container show_bgp_all_summary_wide {
                leaf json {
                    type enumeration {
                        enum json;
                    }
                }                  //json
            }
            container show_bgp_community_local-AS_exact-match {
                leaf wide {
                    type enumeration {
                        enum wide;
                    }
                }                  //wide
            }
            container show_bgp_community_local-AS_json {
                leaf detail {
                    type enumeration {
                        enum detail;
                    }
                }                  //detail
            }
            container show_bgp_community_no-advertise_exact-match {
                leaf wide {
                    type enumeration {
                        enum wide;
                    }
                }                  //wide
            }
            container show_bgp_community_no-advertise_json {
                leaf detail {
                    type enumeration {
                        enum detail;
                    }
                }                  //detail
            }
            container show_bgp_community_no-export_exact-match {
                leaf wide {
                    type enumeration {
                        enum wide;
                    }
                }                  //wide
            }
            container show_bgp_community_no-export_json {
                leaf detail {
                    type enumeration {
                        enum detail;
                    }
                }                  //detail
            }
            container show_bgp_community_graceful-shutdown_exact-match {
                leaf wide {
                    type enumeration {
                        enum wide;
                    }
                }                  //wide
            }
            container show_bgp_community_graceful-shutdown_json {
                leaf detail {
                    type enumeration {
                        enum detail;
                    }
                }                  //detail
            }
            container show_bgp_community_no-peer_exact-match {
                leaf wide {
                    type enumeration {
                        enum wide;
                    }
                }                  //wide
            }
            container show_bgp_community_no-peer_json {
                leaf detail {
                    type enumeration {
                        enum detail;
                    }
                }                  //detail
            }
            container show_bgp_community_blackhole_exact-match {
                leaf wide {
                    type enumeration {
                        enum wide;
                    }
                }                  //wide
            }
            container show_bgp_community_blackhole_json {
                leaf detail {
                    type enumeration {
                        enum detail;
                    }
                }                  //detail
            }
            container show_bgp_community_llgr-stale_exact-match {
                leaf wide {
                    type enumeration {
                        enum wide;
                    }
                }                  //wide
            }
            container show_bgp_community_llgr-stale_json {
                leaf detail {
                    type enumeration {
                        enum detail;
                    }
                }                  //detail
            }
            container show_bgp_community_no-llgr_exact-match {
                leaf wide {
                    type enumeration {
                        enum wide;
                    }
                }                  //wide
            }
            container show_bgp_community_no-llgr_json {
                leaf detail {
                    type enumeration {
                        enum detail;
                    }
                }                  //detail
            }
            container show_bgp_community_accept-own_exact-match {
                leaf wide {
                    type enumeration {
                        enum wide;
                    }
                }                  //wide
            }
            container show_bgp_community_accept-own_json {
                leaf detail {
                    type enumeration {
                        enum detail;
                    }
                }                  //detail
            }
            container show_bgp_community_accept-own-nexthop_exact-match {
                leaf wide {
                    type enumeration {
                        enum wide;
                    }
                }                  //wide
            }
            container show_bgp_community_accept-own-nexthop_json {
                leaf detail {
                    type enumeration {
                        enum detail;
                    }
                }                  //detail
            }
            container show_bgp_community_route-filter-v6_exact-match {
                leaf wide {
                    type enumeration {
                        enum wide;
                    }
                }                  //wide
            }
            container show_bgp_community_route-filter-v6_json {
                leaf detail {
                    type enumeration {
                        enum detail;
                    }
                }                  //detail
            }
            container show_bgp_community_route-filter-v4_exact-match {
                leaf wide {
                    type enumeration {
                        enum wide;
                    }
                }                  //wide
            }
            container show_bgp_community_route-filter-v4_json {
                leaf detail {
                    type enumeration {
                        enum detail;
                    }
                }                  //detail
            }
            container show_bgp_community_route-filter-translated-v6_exact-match {
                leaf wide {
                    type enumeration {
                        enum wide;
                    }
                }                  //wide
            }
            container show_bgp_community_route-filter-translated-v6_json {
                leaf detail {
                    type enumeration {
                        enum detail;
                    }
                }                  //detail
            }
            container show_bgp_community_route-filter-translated-v4_exact-match {
                leaf wide {
                    type enumeration {
                        enum wide;
                    }
                }                  //wide
            }
            container show_bgp_community_route-filter-translated-v4_json {
                leaf detail {
                    type enumeration {
                        enum detail;
                    }
                }                  //detail
            }
            container show_bgp_community_exact-match_json {
                leaf detail {
                    type enumeration {
                        enum detail;
                    }
                }                  //detail
            }
            container show_bgp_summary_established_terse {
                leaf json {
                    type enumeration {
                        enum json;
                    }
                }                  //json
            }
            container show_bgp_summary_established_wide {
                leaf json {
                    type enumeration {
                        enum json;
                    }
                }                  //json
            }
            container show_bgp_summary_failed_terse {
                leaf json {
                    type enumeration {
                        enum json;
                    }
                }                  //json
            }
            container show_bgp_summary_failed_wide {
                leaf json {
                    type enumeration {
                        enum json;
                    }
                }                  //json
            }
            container show_bgp_summary_terse_wide {
                leaf json {
                    type enumeration {
                        enum json;
                    }
                }                  //json
            }
            container show_bgp_l2vpn_evpn_statistics {
                leaf json {
                    type enumeration {
                        enum json;
                    }
                }                  //json
            }
            container show_bgp_l2vpn_evpn_all {
                leaf tags {
                    type enumeration {
                        enum tags;
                    }
                }                  //tags
            }
            container show_bgp_l2vpn_evpn_summary {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_bgp_l2vpn_evpn_es {
                leaf ES_ID {
                    type string;
                }                  //NAME
                leaf json {
                    type enumeration {
                        enum json;
                    }
                }                  //json
            }
            container show_bgp_l2vpn_evpn_es-evi {
                leaf vni {
                    type enumeration {
                        enum vni;
                    }
                }                  //vni
                leaf VNI {
                    type int32;
                }                  //(1-16777215)
                leaf json {
                    type enumeration {
                        enum json;
                    }
                }                  //json
                leaf json_detail {
                    type enumeration {
                        enum json_detail;
                    }
                }                  //detail
                leaf detail {
                    type enumeration {
                        enum detail;
                    }
                }                  //detail
            }
            container show_bgp_l2vpn_evpn_es-vrf {
                leaf ES_ID {
                    type string;
                }                  //NAME
                leaf json {
                    type enumeration {
                        enum json;
                    }
                }                  //json
            }
            container show_bgp_l2vpn_evpn_import-rt {
                leaf json {
                    type enumeration {
                        enum json;
                    }
                }                  //json
            }
            container show_bgp_l2vpn_evpn_next-hops {
                leaf json {
                    type enumeration {
                        enum json;
                    }
                }                  //json
            }
            container show_bgp_l2vpn_evpn_route {
                leaf type {
                    type enumeration {
                        enum type;
                    }
                }                  //type
                leaf CHOICE_CASE {
                    type enumeration {
                        enum ead;
                        enum 1;
                        enum macip;
                        enum 2;
                        enum multicast;
                        enum 3;
                        enum es;
                        enum 4;
                        enum prefix;
                        enum 5;
                    }
                }                  //<ead|1|macip|2|multicast|3|es|4|prefix|5> ['EAD (Type-1) route', 'EAD (Type-1) route', 'MAC-IP (Type-2) route', 'MAC-IP (Type-2) route', 'Multicast (Type-3) route', 'Multicast (Type-3) route', 'Ethernet Segment (Type-4) route', 'Ethernet Segment (Type-4) route', 'Prefix (Type-5) route', 'Prefix (Type-5) route']
                leaf json {
                    type enumeration {
                        enum json;
                    }
                }                  //json
                leaf esi {
                    type enumeration {
                        enum esi;
                    }
                }                  //esi
                leaf ESI_ID {
                    type string;
                }                  //ESI
                leaf rd {
                    type enumeration {
                        enum rd;
                    }
                }                  //rd
                leaf BGP_IDENTIFIER {
                    type string;
                }                  //ASN:NN_OR_IP-ADDRESS:NN
                leaf all {
                    type enumeration {
                        enum all;
                    }
                }
                leaf mac {
                    type enumeration {
                        enum mac;
                    }
                }                  //mac
                leaf MAC_ADDRESS_ {
                    type string;
                }                  //WORD
                leaf ip {
                    type enumeration {
                        enum ip;
                    }
                }                  //ip
                leaf IP_ADDRESS {
                    type string;
                }                  //WORD
            }
            container show_bgp_l2vpn_evpn_vni {
                leaf VNI_NUMBER {
                    type int32;
                }                  //(1-16777215)
                leaf json {
                    type enumeration {
                        enum json;
                    }
                }                  //json
                leaf remote-ip-hash {
                    type enumeration {
                        enum remote-ip-hash;
                    }
                }                  //remote-ip-hash
            }
            container show_bgp_l2vpn_evpn_vrf-import-rt {
                leaf json {
                    type enumeration {
                        enum json;
                    }
                }                  //json
            }
            container show_bgp_vrf_all_update-groups {
                leaf json {
                    type enumeration {
                        enum json;
                    }
                }                  //json
            }
            container show_bgp_view_all_update-groups {
                leaf json {
                    type enumeration {
                        enum json;
                    }
                }                  //json
            }
            container show_bgp_vni_all_detail {
                leaf json {
                    type enumeration {
                        enum json;
                    }
                }                  //json
            }
            container show_bgp_vni_all_type {
                leaf EAD_TYPE {
                    type enumeration {
                        enum 1;
                        enum ead;
                    }
                }                  //<1|ead> ['EAD (Type-1) route', 'EAD (Type-1) route']
                leaf vtep {
                    type enumeration {
                        enum vtep;
                    }
                }                  //vtep
                leaf REMOTE_VTEP_IP_ADDRESS {
                    type inet:ipv4-address;
                }                  //A.B.C.D
                leaf CHOICE_CASE {
                    type enumeration {
                        enum detail;
                        enum json;
                    }
                }                  //<detail|json> ['Print Detailed Output', 'JavaScript Object Notation']
                leaf MACIP_TYPE {
                    type enumeration {
                        enum 2;
                        enum macip;
                    }
                }                  //<2|macip> ['MAC-IP (Type-2) route', 'MAC-IP (Type-2) route']
                leaf ip {
                    type enumeration {
                        enum ip;
                    }
                }                  //ip
                leaf ip_vtep {
                    type enumeration {
                        enum ip_vtep;
                    }
                }                  //vtep
                leaf mac {
                    type enumeration {
                        enum mac;
                    }
                }                  //mac
                leaf mac_vtep {
                    type enumeration {
                        enum mac_vtep;
                    }
                }                  //vtep
                leaf MULTICAST_TYPE {
                    type enumeration {
                        enum 3;
                        enum multicast;
                    }
                }                  //<3|multicast> ['Multicast (Type-3) route', 'Multicast (Type-3) route']
            }
            container show_evpn_arp-cache_vni_all {
                leaf json {
                    type enumeration {
                        enum json;
                    }
                }                  //json
            }
            container show_evpn_mac_vni_all {
                leaf json {
                    type enumeration {
                        enum json;
                    }
                }                  //json
                leaf vtep {
                    type enumeration {
                        enum vtep;
                    }
                }                  //vtep
                leaf REMOTE_VTEP_IP_ADDRESS {
                    type inet:ipv4-address;
                }                  //A.B.C.D
            }
            container show_evpn_next-hops_vni_all {
                leaf json {
                    type enumeration {
                        enum json;
                    }
                }                  //json
            }
            container show_evpn_rmac_vni_all {
                leaf json {
                    type enumeration {
                        enum json;
                    }
                }                  //json
            }
            container show_interface_vrf_all_brief {
                leaf json {
                    type enumeration {
                        enum json;
                    }
                }                  //json
            }
            container show_isis_mpls-te_database_vertex {
                leaf MPLS-TE_VERTEX_ID {
                    type string;
                }                  //WORD
                leaf detail {
                    type enumeration {
                        enum detail;
                    }
                }                  //detail
                leaf json {
                    type enumeration {
                        enum json;
                    }
                }                  //json
            }
            container show_isis_mpls-te_database_edge {
                leaf MPLS-TE_EDGE_ID {
                    type inet:ipv4-address;
                }                  //A.B.C.D
                leaf detail {
                    type enumeration {
                        enum detail;
                    }
                }                  //detail
                leaf json {
                    type enumeration {
                        enum json;
                    }
                }                  //json
            }
            container show_isis_mpls-te_database_subnet {
                leaf IPV4_PREFIX {
                    type inet:ipv4-prefix;
                }                  //A.B.C.D/M
                leaf detail {
                    type enumeration {
                        enum detail;
                    }
                }                  //detail
                leaf json {
                    type enumeration {
                        enum json;
                    }
                }                  //json
                leaf MPLS-TE_SUBNET_ID {
                    type inet:ipv6-prefix;
                }                  //X:X::X:X/M
            }
            container clear_ipv6_ospf6_auth-counters_interface {
                leaf INTERFACE_NAME {
                    type string;
                }                  //IFNAME
            }
            container show_ip_bgp_all_cidr-only_json {
                leaf detail {
                    type enumeration {
                        enum detail;
                    }
                }                  //detail
            }
            container show_ip_bgp_all_dampening_parameters {
                leaf json {
                    type enumeration {
                        enum json;
                    }
                }                  //json
            }
            container show_ip_bgp_all_community_local-AS {
                leaf wide {
                    type enumeration {
                        enum wide;
                    }
                }                  //wide
            }
            container show_ip_bgp_all_community_no-advertise {
                leaf wide {
                    type enumeration {
                        enum wide;
                    }
                }                  //wide
            }
            container show_ip_bgp_all_community_no-export {
                leaf wide {
                    type enumeration {
                        enum wide;
                    }
                }                  //wide
            }
            container show_ip_bgp_all_community_graceful-shutdown {
                leaf wide {
                    type enumeration {
                        enum wide;
                    }
                }                  //wide
            }
            container show_ip_bgp_all_community_no-peer {
                leaf wide {
                    type enumeration {
                        enum wide;
                    }
                }                  //wide
            }
            container show_ip_bgp_all_community_blackhole {
                leaf wide {
                    type enumeration {
                        enum wide;
                    }
                }                  //wide
            }
            container show_ip_bgp_all_community_llgr-stale {
                leaf wide {
                    type enumeration {
                        enum wide;
                    }
                }                  //wide
            }
            container show_ip_bgp_all_community_no-llgr {
                leaf wide {
                    type enumeration {
                        enum wide;
                    }
                }                  //wide
            }
            container show_ip_bgp_all_community_accept-own {
                leaf wide {
                    type enumeration {
                        enum wide;
                    }
                }                  //wide
            }
            container show_ip_bgp_all_community_accept-own-nexthop {
                leaf wide {
                    type enumeration {
                        enum wide;
                    }
                }                  //wide
            }
            container show_ip_bgp_all_community_route-filter-v6 {
                leaf wide {
                    type enumeration {
                        enum wide;
                    }
                }                  //wide
            }
            container show_ip_bgp_all_community_route-filter-v4 {
                leaf wide {
                    type enumeration {
                        enum wide;
                    }
                }                  //wide
            }
            container show_ip_bgp_all_community_route-filter-translated-v6 {
                leaf wide {
                    type enumeration {
                        enum wide;
                    }
                }                  //wide
            }
            container show_ip_bgp_all_community_route-filter-translated-v4 {
                leaf wide {
                    type enumeration {
                        enum wide;
                    }
                }                  //wide
            }
            container show_ip_bgp_all_community_exact-match {
                leaf wide {
                    type enumeration {
                        enum wide;
                    }
                }                  //wide
            }
            container show_ip_bgp_all_community_json {
                leaf detail {
                    type enumeration {
                        enum detail;
                    }
                }                  //detail
            }
            container show_ip_bgp_all_detail-routes_json {
                leaf detail {
                    type enumeration {
                        enum detail;
                    }
                }                  //detail
            }
            container show_ip_bgp_all_summary_established {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_ip_bgp_all_summary_failed {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_ip_bgp_all_summary_terse {
                leaf json {
                    type enumeration {
                        enum json;
                    }
                }                  //json
            }
            container show_ip_bgp_all_summary_wide {
                leaf json {
                    type enumeration {
                        enum json;
                    }
                }                  //json
            }
            container show_ip_bgp_community_local-AS_exact-match {
                leaf wide {
                    type enumeration {
                        enum wide;
                    }
                }                  //wide
            }
            container show_ip_bgp_community_local-AS_json {
                leaf detail {
                    type enumeration {
                        enum detail;
                    }
                }                  //detail
            }
            container show_ip_bgp_community_no-advertise_exact-match {
                leaf wide {
                    type enumeration {
                        enum wide;
                    }
                }                  //wide
            }
            container show_ip_bgp_community_no-advertise_json {
                leaf detail {
                    type enumeration {
                        enum detail;
                    }
                }                  //detail
            }
            container show_ip_bgp_community_no-export_exact-match {
                leaf wide {
                    type enumeration {
                        enum wide;
                    }
                }                  //wide
            }
            container show_ip_bgp_community_no-export_json {
                leaf detail {
                    type enumeration {
                        enum detail;
                    }
                }                  //detail
            }
            container show_ip_bgp_community_graceful-shutdown_exact-match {
                leaf wide {
                    type enumeration {
                        enum wide;
                    }
                }                  //wide
            }
            container show_ip_bgp_community_graceful-shutdown_json {
                leaf detail {
                    type enumeration {
                        enum detail;
                    }
                }                  //detail
            }
            container show_ip_bgp_community_no-peer_exact-match {
                leaf wide {
                    type enumeration {
                        enum wide;
                    }
                }                  //wide
            }
            container show_ip_bgp_community_no-peer_json {
                leaf detail {
                    type enumeration {
                        enum detail;
                    }
                }                  //detail
            }
            container show_ip_bgp_community_blackhole_exact-match {
                leaf wide {
                    type enumeration {
                        enum wide;
                    }
                }                  //wide
            }
            container show_ip_bgp_community_blackhole_json {
                leaf detail {
                    type enumeration {
                        enum detail;
                    }
                }                  //detail
            }
            container show_ip_bgp_community_llgr-stale_exact-match {
                leaf wide {
                    type enumeration {
                        enum wide;
                    }
                }                  //wide
            }
            container show_ip_bgp_community_llgr-stale_json {
                leaf detail {
                    type enumeration {
                        enum detail;
                    }
                }                  //detail
            }
            container show_ip_bgp_community_no-llgr_exact-match {
                leaf wide {
                    type enumeration {
                        enum wide;
                    }
                }                  //wide
            }
            container show_ip_bgp_community_no-llgr_json {
                leaf detail {
                    type enumeration {
                        enum detail;
                    }
                }                  //detail
            }
            container show_ip_bgp_community_accept-own_exact-match {
                leaf wide {
                    type enumeration {
                        enum wide;
                    }
                }                  //wide
            }
            container show_ip_bgp_community_accept-own_json {
                leaf detail {
                    type enumeration {
                        enum detail;
                    }
                }                  //detail
            }
            container show_ip_bgp_community_accept-own-nexthop_exact-match {
                leaf wide {
                    type enumeration {
                        enum wide;
                    }
                }                  //wide
            }
            container show_ip_bgp_community_accept-own-nexthop_json {
                leaf detail {
                    type enumeration {
                        enum detail;
                    }
                }                  //detail
            }
            container show_ip_bgp_community_route-filter-v6_exact-match {
                leaf wide {
                    type enumeration {
                        enum wide;
                    }
                }                  //wide
            }
            container show_ip_bgp_community_route-filter-v6_json {
                leaf detail {
                    type enumeration {
                        enum detail;
                    }
                }                  //detail
            }
            container show_ip_bgp_community_route-filter-v4_exact-match {
                leaf wide {
                    type enumeration {
                        enum wide;
                    }
                }                  //wide
            }
            container show_ip_bgp_community_route-filter-v4_json {
                leaf detail {
                    type enumeration {
                        enum detail;
                    }
                }                  //detail
            }
            container show_ip_bgp_community_route-filter-translated-v6_exact-match {
                leaf wide {
                    type enumeration {
                        enum wide;
                    }
                }                  //wide
            }
            container show_ip_bgp_community_route-filter-translated-v6_json {
                leaf detail {
                    type enumeration {
                        enum detail;
                    }
                }                  //detail
            }
            container show_ip_bgp_community_route-filter-translated-v4_exact-match {
                leaf wide {
                    type enumeration {
                        enum wide;
                    }
                }                  //wide
            }
            container show_ip_bgp_community_route-filter-translated-v4_json {
                leaf detail {
                    type enumeration {
                        enum detail;
                    }
                }                  //detail
            }
            container show_ip_bgp_community_exact-match_json {
                leaf detail {
                    type enumeration {
                        enum detail;
                    }
                }                  //detail
            }
            container show_ip_bgp_summary_established_terse {
                leaf json {
                    type enumeration {
                        enum json;
                    }
                }                  //json
            }
            container show_ip_bgp_summary_established_wide {
                leaf json {
                    type enumeration {
                        enum json;
                    }
                }                  //json
            }
            container show_ip_bgp_summary_failed_terse {
                leaf json {
                    type enumeration {
                        enum json;
                    }
                }                  //json
            }
            container show_ip_bgp_summary_failed_wide {
                leaf json {
                    type enumeration {
                        enum json;
                    }
                }                  //json
            }
            container show_ip_bgp_summary_terse_wide {
                leaf json {
                    type enumeration {
                        enum json;
                    }
                }                  //json
            }
            container show_ip_bgp_l2vpn_evpn_statistics {
                leaf json {
                    type enumeration {
                        enum json;
                    }
                }                  //json
            }
            container show_ip_bgp_l2vpn_evpn_all {
                leaf tags {
                    type enumeration {
                        enum tags;
                    }
                }                  //tags
            }
            container show_ip_igmp_vrf_all_groups {
                leaf json {
                    type enumeration {
                        enum json;
                    }
                }                  //json
            }
            container show_ip_igmp_vrf_all_interface {
                leaf INTERFACE_NAME {
                    type string;
                }                  //WORD
                leaf json {
                    type enumeration {
                        enum json;
                    }
                }                  //json
            }
            container show_ip_igmp_vrf_all_join {
                leaf json {
                    type enumeration {
                        enum json;
                    }
                }                  //json
            }
            container show_ip_mroute_vrf_all_fill {
                leaf json {
                    type enumeration {
                        enum json;
                    }
                }                  //json
            }
            container show_ip_mroute_vrf_all_count {
                leaf json {
                    type enumeration {
                        enum json;
                    }
                }                  //json
            }
            container show_ip_mroute_vrf_all_summary {
                leaf json {
                    type enumeration {
                        enum json;
                    }
                }                  //json
            }
            container show_ip_msdp_vrf_all_mesh-group {
                leaf json {
                    type enumeration {
                        enum json;
                    }
                }                  //json
            }
            container show_ip_msdp_vrf_all_peer {
                leaf PEER_IP_ADDRESS {
                    type inet:ipv4-address;
                }                  //A.B.C.D
                leaf json {
                    type enumeration {
                        enum json;
                    }
                }                  //json
            }
            container show_ip_msdp_vrf_all_sa {
                leaf SOURCE_OR_GROUP_IP {
                    type inet:ipv4-address;
                }                  //A.B.C.D
                leaf GROUP_IP {
                    type inet:ipv4-address;
                }                  //A.B.C.D
                leaf json {
                    type enumeration {
                        enum json;
                    }
                }                  //json
            }
            container show_ip_multicast_count_vrf_all {
                leaf json {
                    type enumeration {
                        enum json;
                    }
                }                  //json
            }
            container show_ip_nht_vrf_all_mrib {
                leaf json {
                    type enumeration {
                        enum json;
                    }
                }                  //json
            }
            container show_ip_import-check_vrf_all_mrib {
                leaf json {
                    type enumeration {
                        enum json;
                    }
                }                  //json
            }
            container show_ip_ospf_neighbor_detail_all {
                leaf json {
                    type enumeration {
                        enum json;
                    }
                }                  //json
            }
            container show_ip_ospf_database_segment-routing_self-originate {
                leaf json {
                    type enumeration {
                        enum json;
                    }
                }                  //json
            }
            container show_ip_ospf_graceful-restart_helper_detail {
                leaf json {
                    type enumeration {
                        enum json;
                    }
                }                  //json
            }
            container show_ip_ospf_mpls-te_database_vertex {
                leaf adv-router {
                    type inet:ipv4-address;
                }                  //A.B.C.D
                leaf self-originate {
                    type enumeration {
                        enum self-originate;
                    }
                }
                leaf verbose {
                    type enumeration {
                        enum verbose;
                    }
                }                  //verbose
                leaf json {
                    type enumeration {
                        enum json;
                    }
                }                  //json
            }
            container show_ip_ospf_mpls-te_database_edge {
                leaf MPLS-TE_EDGE_ID {
                    type inet:ipv4-address;
                }                  //A.B.C.D
                leaf verbose {
                    type enumeration {
                        enum verbose;
                    }
                }                  //verbose
                leaf json {
                    type enumeration {
                        enum json;
                    }
                }                  //json
            }
            container show_ip_ospf_mpls-te_database_subnet {
                leaf IPV4_PREFIX {
                    type inet:ipv4-prefix;
                }                  //A.B.C.D/M
                leaf verbose {
                    type enumeration {
                        enum verbose;
                    }
                }                  //verbose
                leaf json {
                    type enumeration {
                        enum json;
                    }
                }                  //json
            }
            container show_ip_pim_mlag_interface_detail {
                leaf json {
                    type enumeration {
                        enum json;
                    }
                }                  //json
            }
            container show_ip_pim_vrf_all_interface {
                leaf INTERFACE_NAME {
                    type string;
                }                  //WORD
                leaf json {
                    type enumeration {
                        enum json;
                    }
                }                  //json
            }
            container show_ip_pim_vrf_all_join {
                leaf json {
                    type enumeration {
                        enum json;
                    }
                }                  //json
            }
            container show_ip_pim_vrf_all_neighbor {
                leaf NAME_OF_INTERFACE_OR {
                    type string;
                }                  //WORD
                leaf json {
                    type enumeration {
                        enum json;
                    }
                }                  //json
            }
            container show_ip_pim_vrf_all_rp-info {
                leaf IPV4_PREFIX {
                    type inet:ipv4-prefix;
                }                  //A.B.C.D/M
                leaf json {
                    type enumeration {
                        enum json;
                    }
                }                  //json
            }
            container show_ip_pim_vrf_all_rpf {
                leaf json {
                    type enumeration {
                        enum json;
                    }
                }                  //json
            }
            container show_ip_pim_vrf_all_state {
                leaf UNICAST_OR_MULTICAST_ADDRESS {
                    type inet:ipv4-address;
                }                  //A.B.C.D
                leaf MULTICAST_ADDRESS {
                    type inet:ipv4-address;
                }                  //A.B.C.D
                leaf json {
                    type enumeration {
                        enum json;
                    }
                }                  //json
            }
            container show_ip_pim_vrf_all_upstream {
                leaf json {
                    type enumeration {
                        enum json;
                    }
                }                  //json
            }
            container show_ipv6_mroute_vrf_all_fill {
                leaf json {
                    type enumeration {
                        enum json;
                    }
                }                  //json
            }
            container show_ipv6_mroute_vrf_all_count {
                leaf json {
                    type enumeration {
                        enum json;
                    }
                }                  //json
            }
            container show_ipv6_mroute_vrf_all_summary {
                leaf json {
                    type enumeration {
                        enum json;
                    }
                }                  //json
            }
            container show_ipv6_multicast_count_vrf_all {
                leaf json {
                    type enumeration {
                        enum json;
                    }
                }                  //json
            }
            container show_ipv6_nht_vrf_all_mrib {
                leaf json {
                    type enumeration {
                        enum json;
                    }
                }                  //json
            }
            container show_ipv6_import-check_vrf_all_mrib {
                leaf json {
                    type enumeration {
                        enum json;
                    }
                }                  //json
            }
            container show_ipv6_ospf6_interface_prefix_detail {
                leaf json {
                    type enumeration {
                        enum json;
                    }
                }                  //json
            }
            container show_ipv6_pim_vrf_all_interface {
                leaf INTERFACE_NAME {
                    type string;
                }                  //WORD
                leaf json {
                    type enumeration {
                        enum json;
                    }
                }                  //json
            }
            container show_ipv6_pim_vrf_all_join {
                leaf json {
                    type enumeration {
                        enum json;
                    }
                }                  //json
            }
            container show_ipv6_pim_vrf_all_neighbor {
                leaf NAME_OF_INTERFACE_OR {
                    type string;
                }                  //WORD
                leaf json {
                    type enumeration {
                        enum json;
                    }
                }                  //json
            }
            container show_ipv6_pim_vrf_all_rp-info {
                leaf MULTICAST_GROUP_RANGE {
                    type inet:ipv6-prefix;
                }                  //X:X::X:X/M
                leaf json {
                    type enumeration {
                        enum json;
                    }
                }                  //json
            }
            container show_ipv6_pim_vrf_all_rpf {
                leaf json {
                    type enumeration {
                        enum json;
                    }
                }                  //json
            }
            container show_ipv6_pim_vrf_all_state {
                leaf UNICAST_OR_MULTICAST_ADDRESS {
                    type inet:ipv6-address;
                }                  //X:X::X:X
                leaf MULTICAST_ADDRESS {
                    type inet:ipv6-address;
                }                  //X:X::X:X
                leaf json {
                    type enumeration {
                        enum json;
                    }
                }                  //json
            }
            container show_ipv6_pim_vrf_all_upstream {
                leaf json {
                    type enumeration {
                        enum json;
                    }
                }                  //json
            }
            container show_bgp_all_community_local-AS_exact-match {
                leaf wide {
                    type enumeration {
                        enum wide;
                    }
                }                  //wide
            }
            container show_bgp_all_community_local-AS_json {
                leaf detail {
                    type enumeration {
                        enum detail;
                    }
                }                  //detail
            }
            container show_bgp_all_community_no-advertise_exact-match {
                leaf wide {
                    type enumeration {
                        enum wide;
                    }
                }                  //wide
            }
            container show_bgp_all_community_no-advertise_json {
                leaf detail {
                    type enumeration {
                        enum detail;
                    }
                }                  //detail
            }
            container show_bgp_all_community_no-export_exact-match {
                leaf wide {
                    type enumeration {
                        enum wide;
                    }
                }                  //wide
            }
            container show_bgp_all_community_no-export_json {
                leaf detail {
                    type enumeration {
                        enum detail;
                    }
                }                  //detail
            }
            container show_bgp_all_community_graceful-shutdown_exact-match {
                leaf wide {
                    type enumeration {
                        enum wide;
                    }
                }                  //wide
            }
            container show_bgp_all_community_graceful-shutdown_json {
                leaf detail {
                    type enumeration {
                        enum detail;
                    }
                }                  //detail
            }
            container show_bgp_all_community_no-peer_exact-match {
                leaf wide {
                    type enumeration {
                        enum wide;
                    }
                }                  //wide
            }
            container show_bgp_all_community_no-peer_json {
                leaf detail {
                    type enumeration {
                        enum detail;
                    }
                }                  //detail
            }
            container show_bgp_all_community_blackhole_exact-match {
                leaf wide {
                    type enumeration {
                        enum wide;
                    }
                }                  //wide
            }
            container show_bgp_all_community_blackhole_json {
                leaf detail {
                    type enumeration {
                        enum detail;
                    }
                }                  //detail
            }
            container show_bgp_all_community_llgr-stale_exact-match {
                leaf wide {
                    type enumeration {
                        enum wide;
                    }
                }                  //wide
            }
            container show_bgp_all_community_llgr-stale_json {
                leaf detail {
                    type enumeration {
                        enum detail;
                    }
                }                  //detail
            }
            container show_bgp_all_community_no-llgr_exact-match {
                leaf wide {
                    type enumeration {
                        enum wide;
                    }
                }                  //wide
            }
            container show_bgp_all_community_no-llgr_json {
                leaf detail {
                    type enumeration {
                        enum detail;
                    }
                }                  //detail
            }
            container show_bgp_all_community_accept-own_exact-match {
                leaf wide {
                    type enumeration {
                        enum wide;
                    }
                }                  //wide
            }
            container show_bgp_all_community_accept-own_json {
                leaf detail {
                    type enumeration {
                        enum detail;
                    }
                }                  //detail
            }
            container show_bgp_all_community_accept-own-nexthop_exact-match {
                leaf wide {
                    type enumeration {
                        enum wide;
                    }
                }                  //wide
            }
            container show_bgp_all_community_accept-own-nexthop_json {
                leaf detail {
                    type enumeration {
                        enum detail;
                    }
                }                  //detail
            }
            container show_bgp_all_community_route-filter-v6_exact-match {
                leaf wide {
                    type enumeration {
                        enum wide;
                    }
                }                  //wide
            }
            container show_bgp_all_community_route-filter-v6_json {
                leaf detail {
                    type enumeration {
                        enum detail;
                    }
                }                  //detail
            }
            container show_bgp_all_community_route-filter-v4_exact-match {
                leaf wide {
                    type enumeration {
                        enum wide;
                    }
                }                  //wide
            }
            container show_bgp_all_community_route-filter-v4_json {
                leaf detail {
                    type enumeration {
                        enum detail;
                    }
                }                  //detail
            }
            container show_bgp_all_community_route-filter-translated-v6_exact-match {
                leaf wide {
                    type enumeration {
                        enum wide;
                    }
                }                  //wide
            }
            container show_bgp_all_community_route-filter-translated-v6_json {
                leaf detail {
                    type enumeration {
                        enum detail;
                    }
                }                  //detail
            }
            container show_bgp_all_community_route-filter-translated-v4_exact-match {
                leaf wide {
                    type enumeration {
                        enum wide;
                    }
                }                  //wide
            }
            container show_bgp_all_community_route-filter-translated-v4_json {
                leaf detail {
                    type enumeration {
                        enum detail;
                    }
                }                  //detail
            }
            container show_bgp_all_community_exact-match_json {
                leaf detail {
                    type enumeration {
                        enum detail;
                    }
                }                  //detail
            }
            container show_bgp_all_summary_established_terse {
                leaf json {
                    type enumeration {
                        enum json;
                    }
                }                  //json
            }
            container show_bgp_all_summary_established_wide {
                leaf json {
                    type enumeration {
                        enum json;
                    }
                }                  //json
            }
            container show_bgp_all_summary_failed_terse {
                leaf json {
                    type enumeration {
                        enum json;
                    }
                }                  //json
            }
            container show_bgp_all_summary_failed_wide {
                leaf json {
                    type enumeration {
                        enum json;
                    }
                }                  //json
            }
            container show_bgp_all_summary_terse_wide {
                leaf json {
                    type enumeration {
                        enum json;
                    }
                }                  //json
            }
            container show_bgp_community_local-AS_exact-match_json {
                leaf detail {
                    type enumeration {
                        enum detail;
                    }
                }                  //detail
            }
            container show_bgp_community_no-advertise_exact-match_json {
                leaf detail {
                    type enumeration {
                        enum detail;
                    }
                }                  //detail
            }
            container show_bgp_community_no-export_exact-match_json {
                leaf detail {
                    type enumeration {
                        enum detail;
                    }
                }                  //detail
            }
            container show_bgp_community_graceful-shutdown_exact-match_json {
                leaf detail {
                    type enumeration {
                        enum detail;
                    }
                }                  //detail
            }
            container show_bgp_community_no-peer_exact-match_json {
                leaf detail {
                    type enumeration {
                        enum detail;
                    }
                }                  //detail
            }
            container show_bgp_community_blackhole_exact-match_json {
                leaf detail {
                    type enumeration {
                        enum detail;
                    }
                }                  //detail
            }
            container show_bgp_community_llgr-stale_exact-match_json {
                leaf detail {
                    type enumeration {
                        enum detail;
                    }
                }                  //detail
            }
            container show_bgp_community_no-llgr_exact-match_json {
                leaf detail {
                    type enumeration {
                        enum detail;
                    }
                }                  //detail
            }
            container show_bgp_community_accept-own_exact-match_json {
                leaf detail {
                    type enumeration {
                        enum detail;
                    }
                }                  //detail
            }
            container show_bgp_community_accept-own-nexthop_exact-match_json {
                leaf detail {
                    type enumeration {
                        enum detail;
                    }
                }                  //detail
            }
            container show_bgp_community_route-filter-v6_exact-match_json {
                leaf detail {
                    type enumeration {
                        enum detail;
                    }
                }                  //detail
            }
            container show_bgp_community_route-filter-v4_exact-match_json {
                leaf detail {
                    type enumeration {
                        enum detail;
                    }
                }                  //detail
            }
            container show_bgp_community_route-filter-translated-v6_exact-match_json {
                leaf detail {
                    type enumeration {
                        enum detail;
                    }
                }                  //detail
            }
            container show_bgp_community_route-filter-translated-v4_exact-match_json {
                leaf detail {
                    type enumeration {
                        enum detail;
                    }
                }                  //detail
            }
            container show_bgp_summary_established_terse_wide {
                leaf json {
                    type enumeration {
                        enum json;
                    }
                }                  //json
            }
            container show_bgp_summary_failed_terse_wide {
                leaf json {
                    type enumeration {
                        enum json;
                    }
                }                  //json
            }
            container show_bgp_l2vpn_evpn_all_overlay {
                leaf json {
                    type enumeration {
                        enum json;
                    }
                }                  //json
            }
            container show_bgp_l2vpn_evpn_summary_established {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_bgp_l2vpn_evpn_summary_failed {
                leaf neighbor {
                    type enumeration {
                        enum neighbor;
                    }
                }                  //neighbor
                leaf IP_ADDRESS {
                    type union {
                        type inet:ipv4-address;
                        type inet:ipv6-address;
                        type string;
                    }
                }                  //<A.B.C.D|X:X::X:X|WORD>
                leaf terse {
                    type enumeration {
                        enum terse;
                    }
                }                  //terse
                leaf terse_json {
                    type enumeration {
                        enum terse_json;
                    }
                }                  //json
                leaf wide {
                    type enumeration {
                        enum wide;
                    }
                }                  //wide
                leaf wide_json {
                    type enumeration {
                        enum wide_json;
                    }
                }                  //json
                leaf json {
                    type enumeration {
                        enum json;
                    }
                }                  //json
                leaf terse_wide {
                    type enumeration {
                        enum terse_wide;
                    }
                }                  //terse_wide
                leaf terse_wide_json {
                    type enumeration {
                        enum terse_wide_json;
                    }
                }                  //json
                leaf remote-as {
                    type enumeration {
                        enum remote-as;
                    }
                }                  //remote-as
                leaf AS_NUMBER {
                    type int32;
                }                  //(1-4294967295)
                leaf BGP_PEER {
                    type enumeration {
                        enum internal;
                        enum external;
                    }
                }                  //<internal|external> ['AS number', 'Internal (iBGP) AS sessions', 'External (eBGP) AS sessions']
            }
            container show_bgp_l2vpn_evpn_summary_terse {
                leaf json {
                    type enumeration {
                        enum json;
                    }
                }                  //json
            }
            container show_bgp_l2vpn_evpn_summary_wide {
                leaf json {
                    type enumeration {
                        enum json;
                    }
                }                  //json
            }
            container show_bgp_l2vpn_evpn_es_detail {
                leaf json {
                    type enumeration {
                        enum json;
                    }
                }                  //json
            }
            container show_bgp_l2vpn_evpn_es-evi_json {
                leaf detail {
                    type enumeration {
                        enum detail;
                    }
                }                  //detail
            }
            container show_bgp_l2vpn_evpn_route_detail {
                leaf type {
                    type enumeration {
                        enum type;
                    }
                }                  //type
                leaf CHOICE_CASE {
                    type enumeration {
                        enum ead;
                        enum 1;
                        enum macip;
                        enum 2;
                        enum multicast;
                        enum 3;
                        enum es;
                        enum 4;
                        enum prefix;
                        enum 5;
                    }
                }                  //<ead|1|macip|2|multicast|3|es|4|prefix|5> ['EAD (Type-1) route', 'EAD (Type-1) route', 'MAC-IP (Type-2) route', 'MAC-IP (Type-2) route', 'Multicast (Type-3) route', 'Multicast (Type-3) route', 'Ethernet Segment (Type-4) route', 'Ethernet Segment (Type-4) route', 'Prefix (Type-5) route', 'Prefix (Type-5) route']
                leaf json {
                    type enumeration {
                        enum json;
                    }
                }                  //json
            }
            container show_bgp_l2vpn_evpn_route_vni {
                leaf VNI_NUMBER {
                    type int32;
                }                  //(1-16777215)
                leaf type {
                    type enumeration {
                        enum type;
                    }
                }                  //type
                leaf CHOICE_CASE {
                    type enumeration {
                        enum ead;
                        enum 1;
                        enum macip;
                        enum 2;
                        enum multicast;
                        enum 3;
                    }
                }                  //<ead|1|macip|2|multicast|3> ['EAD (Type-1) route', 'EAD (Type-1) route', 'MAC-IP (Type-2) route', 'MAC-IP (Type-2) route', 'Multicast (Type-3) route', 'Multicast (Type-3) route']
                leaf json {
                    type enumeration {
                        enum json;
                    }
                }                  //json
                leaf vtep {
                    type enumeration {
                        enum vtep;
                    }
                }                  //vtep
                leaf REMOTE_VTEP_IP_ADDRESS {
                    type inet:ipv4-address;
                }                  //A.B.C.D
                leaf mac {
                    type enumeration {
                        enum mac;
                    }
                }                  //mac
                leaf MAC_ADDRESS_ {
                    type string;
                }                  //WORD
                leaf ip {
                    type enumeration {
                        enum ip;
                    }
                }                  //ip
                leaf IP_ADDRESS {
                    type string;
                }                  //WORD
                leaf multicast {
                    type enumeration {
                        enum multicast;
                    }
                }                  //multicast
                leaf ORIGINATING_ROUTER_IP_ADDRESS {
                    type inet:ipv4-address;
                }                  //A.B.C.D
            }
            container show_evpn_arp-cache_vni_all_detail {
                leaf json {
                    type enumeration {
                        enum json;
                    }
                }                  //json
            }
            container show_evpn_arp-cache_vni_all_duplicate {
                leaf json {
                    type enumeration {
                        enum json;
                    }
                }                  //json
            }
            container show_evpn_mac_vni_all_detail {
                leaf json {
                    type enumeration {
                        enum json;
                    }
                }                  //json
            }
            container show_evpn_mac_vni_all_duplicate {
                leaf json {
                    type enumeration {
                        enum json;
                    }
                }                  //json
            }
            container show_ip_bgp_all_community_local-AS_exact-match {
                leaf wide {
                    type enumeration {
                        enum wide;
                    }
                }                  //wide
            }
            container show_ip_bgp_all_community_local-AS_json {
                leaf detail {
                    type enumeration {
                        enum detail;
                    }
                }                  //detail
            }
            container show_ip_bgp_all_community_no-advertise_exact-match {
                leaf wide {
                    type enumeration {
                        enum wide;
                    }
                }                  //wide
            }
            container show_ip_bgp_all_community_no-advertise_json {
                leaf detail {
                    type enumeration {
                        enum detail;
                    }
                }                  //detail
            }
            container show_ip_bgp_all_community_no-export_exact-match {
                leaf wide {
                    type enumeration {
                        enum wide;
                    }
                }                  //wide
            }
            container show_ip_bgp_all_community_no-export_json {
                leaf detail {
                    type enumeration {
                        enum detail;
                    }
                }                  //detail
            }
            container show_ip_bgp_all_community_graceful-shutdown_exact-match {
                leaf wide {
                    type enumeration {
                        enum wide;
                    }
                }                  //wide
            }
            container show_ip_bgp_all_community_graceful-shutdown_json {
                leaf detail {
                    type enumeration {
                        enum detail;
                    }
                }                  //detail
            }
            container show_ip_bgp_all_community_no-peer_exact-match {
                leaf wide {
                    type enumeration {
                        enum wide;
                    }
                }                  //wide
            }
            container show_ip_bgp_all_community_no-peer_json {
                leaf detail {
                    type enumeration {
                        enum detail;
                    }
                }                  //detail
            }
            container show_ip_bgp_all_community_blackhole_exact-match {
                leaf wide {
                    type enumeration {
                        enum wide;
                    }
                }                  //wide
            }
            container show_ip_bgp_all_community_blackhole_json {
                leaf detail {
                    type enumeration {
                        enum detail;
                    }
                }                  //detail
            }
            container show_ip_bgp_all_community_llgr-stale_exact-match {
                leaf wide {
                    type enumeration {
                        enum wide;
                    }
                }                  //wide
            }
            container show_ip_bgp_all_community_llgr-stale_json {
                leaf detail {
                    type enumeration {
                        enum detail;
                    }
                }                  //detail
            }
            container show_ip_bgp_all_community_no-llgr_exact-match {
                leaf wide {
                    type enumeration {
                        enum wide;
                    }
                }                  //wide
            }
            container show_ip_bgp_all_community_no-llgr_json {
                leaf detail {
                    type enumeration {
                        enum detail;
                    }
                }                  //detail
            }
            container show_ip_bgp_all_community_accept-own_exact-match {
                leaf wide {
                    type enumeration {
                        enum wide;
                    }
                }                  //wide
            }
            container show_ip_bgp_all_community_accept-own_json {
                leaf detail {
                    type enumeration {
                        enum detail;
                    }
                }                  //detail
            }
            container show_ip_bgp_all_community_accept-own-nexthop_exact-match {
                leaf wide {
                    type enumeration {
                        enum wide;
                    }
                }                  //wide
            }
            container show_ip_bgp_all_community_accept-own-nexthop_json {
                leaf detail {
                    type enumeration {
                        enum detail;
                    }
                }                  //detail
            }
            container show_ip_bgp_all_community_route-filter-v6_exact-match {
                leaf wide {
                    type enumeration {
                        enum wide;
                    }
                }                  //wide
            }
            container show_ip_bgp_all_community_route-filter-v6_json {
                leaf detail {
                    type enumeration {
                        enum detail;
                    }
                }                  //detail
            }
            container show_ip_bgp_all_community_route-filter-v4_exact-match {
                leaf wide {
                    type enumeration {
                        enum wide;
                    }
                }                  //wide
            }
            container show_ip_bgp_all_community_route-filter-v4_json {
                leaf detail {
                    type enumeration {
                        enum detail;
                    }
                }                  //detail
            }
            container show_ip_bgp_all_community_route-filter-translated-v6_exact-match {
                leaf wide {
                    type enumeration {
                        enum wide;
                    }
                }                  //wide
            }
            container show_ip_bgp_all_community_route-filter-translated-v6_json {
                leaf detail {
                    type enumeration {
                        enum detail;
                    }
                }                  //detail
            }
            container show_ip_bgp_all_community_route-filter-translated-v4_exact-match {
                leaf wide {
                    type enumeration {
                        enum wide;
                    }
                }                  //wide
            }
            container show_ip_bgp_all_community_route-filter-translated-v4_json {
                leaf detail {
                    type enumeration {
                        enum detail;
                    }
                }                  //detail
            }
            container show_ip_bgp_all_community_exact-match_json {
                leaf detail {
                    type enumeration {
                        enum detail;
                    }
                }                  //detail
            }
            container show_ip_bgp_all_summary_established_terse {
                leaf json {
                    type enumeration {
                        enum json;
                    }
                }                  //json
            }
            container show_ip_bgp_all_summary_established_wide {
                leaf json {
                    type enumeration {
                        enum json;
                    }
                }                  //json
            }
            container show_ip_bgp_all_summary_failed_terse {
                leaf json {
                    type enumeration {
                        enum json;
                    }
                }                  //json
            }
            container show_ip_bgp_all_summary_failed_wide {
                leaf json {
                    type enumeration {
                        enum json;
                    }
                }                  //json
            }
            container show_ip_bgp_all_summary_terse_wide {
                leaf json {
                    type enumeration {
                        enum json;
                    }
                }                  //json
            }
            container show_ip_bgp_community_local-AS_exact-match_json {
                leaf detail {
                    type enumeration {
                        enum detail;
                    }
                }                  //detail
            }
            container show_ip_bgp_community_no-advertise_exact-match_json {
                leaf detail {
                    type enumeration {
                        enum detail;
                    }
                }                  //detail
            }
            container show_ip_bgp_community_no-export_exact-match_json {
                leaf detail {
                    type enumeration {
                        enum detail;
                    }
                }                  //detail
            }
            container show_ip_bgp_community_graceful-shutdown_exact-match_json {
                leaf detail {
                    type enumeration {
                        enum detail;
                    }
                }                  //detail
            }
            container show_ip_bgp_community_no-peer_exact-match_json {
                leaf detail {
                    type enumeration {
                        enum detail;
                    }
                }                  //detail
            }
            container show_ip_bgp_community_blackhole_exact-match_json {
                leaf detail {
                    type enumeration {
                        enum detail;
                    }
                }                  //detail
            }
            container show_ip_bgp_community_llgr-stale_exact-match_json {
                leaf detail {
                    type enumeration {
                        enum detail;
                    }
                }                  //detail
            }
            container show_ip_bgp_community_no-llgr_exact-match_json {
                leaf detail {
                    type enumeration {
                        enum detail;
                    }
                }                  //detail
            }
            container show_ip_bgp_community_accept-own_exact-match_json {
                leaf detail {
                    type enumeration {
                        enum detail;
                    }
                }                  //detail
            }
            container show_ip_bgp_community_accept-own-nexthop_exact-match_json {
                leaf detail {
                    type enumeration {
                        enum detail;
                    }
                }                  //detail
            }
            container show_ip_bgp_community_route-filter-v6_exact-match_json {
                leaf detail {
                    type enumeration {
                        enum detail;
                    }
                }                  //detail
            }
            container show_ip_bgp_community_route-filter-v4_exact-match_json {
                leaf detail {
                    type enumeration {
                        enum detail;
                    }
                }                  //detail
            }
            container show_ip_bgp_community_route-filter-translated-v6_exact-match_json {
                leaf detail {
                    type enumeration {
                        enum detail;
                    }
                }                  //detail
            }
            container show_ip_bgp_community_route-filter-translated-v4_exact-match_json {
                leaf detail {
                    type enumeration {
                        enum detail;
                    }
                }                  //detail
            }
            container show_ip_bgp_summary_established_terse_wide {
                leaf json {
                    type enumeration {
                        enum json;
                    }
                }                  //json
            }
            container show_ip_bgp_summary_failed_terse_wide {
                leaf json {
                    type enumeration {
                        enum json;
                    }
                }                  //json
            }
            container show_ip_bgp_l2vpn_evpn_all_overlay {
                leaf json {
                    type enumeration {
                        enum json;
                    }
                }                  //json
            }
            container show_ip_igmp_vrf_all_interface_detail {
                leaf json {
                    type enumeration {
                        enum json;
                    }
                }                  //json
            }
            container show_ip_msdp_vrf_all_peer_detail {
                leaf json {
                    type enumeration {
                        enum json;
                    }
                }                  //json
            }
            container show_ip_msdp_vrf_all_sa_detail {
                leaf json {
                    type enumeration {
                        enum json;
                    }
                }                  //json
            }
            container show_ip_pim_mlag_vrf_all_interface {
                leaf INTERFACE_NAME {
                    type string;
                }                  //WORD
                leaf json {
                    type enumeration {
                        enum json;
                    }
                }                  //json
            }
            container show_ip_pim_vrf_all_interface_detail {
                leaf json {
                    type enumeration {
                        enum json;
                    }
                }                  //json
            }
            container show_ip_pim_vrf_all_neighbor_detail {
                leaf json {
                    type enumeration {
                        enum json;
                    }
                }                  //json
            }
            container show_ipv6_pim_vrf_all_interface_detail {
                leaf json {
                    type enumeration {
                        enum json;
                    }
                }                  //json
            }
            container show_ipv6_pim_vrf_all_neighbor_detail {
                leaf json {
                    type enumeration {
                        enum json;
                    }
                }                  //json
            }
            container show_bgp_all_community_local-AS_exact-match_json {
                leaf detail {
                    type enumeration {
                        enum detail;
                    }
                }                  //detail
            }
            container show_bgp_all_community_no-advertise_exact-match_json {
                leaf detail {
                    type enumeration {
                        enum detail;
                    }
                }                  //detail
            }
            container show_bgp_all_community_no-export_exact-match_json {
                leaf detail {
                    type enumeration {
                        enum detail;
                    }
                }                  //detail
            }
            container show_bgp_all_community_graceful-shutdown_exact-match_json {
                leaf detail {
                    type enumeration {
                        enum detail;
                    }
                }                  //detail
            }
            container show_bgp_all_community_no-peer_exact-match_json {
                leaf detail {
                    type enumeration {
                        enum detail;
                    }
                }                  //detail
            }
            container show_bgp_all_community_blackhole_exact-match_json {
                leaf detail {
                    type enumeration {
                        enum detail;
                    }
                }                  //detail
            }
            container show_bgp_all_community_llgr-stale_exact-match_json {
                leaf detail {
                    type enumeration {
                        enum detail;
                    }
                }                  //detail
            }
            container show_bgp_all_community_no-llgr_exact-match_json {
                leaf detail {
                    type enumeration {
                        enum detail;
                    }
                }                  //detail
            }
            container show_bgp_all_community_accept-own_exact-match_json {
                leaf detail {
                    type enumeration {
                        enum detail;
                    }
                }                  //detail
            }
            container show_bgp_all_community_accept-own-nexthop_exact-match_json {
                leaf detail {
                    type enumeration {
                        enum detail;
                    }
                }                  //detail
            }
            container show_bgp_all_community_route-filter-v6_exact-match_json {
                leaf detail {
                    type enumeration {
                        enum detail;
                    }
                }                  //detail
            }
            container show_bgp_all_community_route-filter-v4_exact-match_json {
                leaf detail {
                    type enumeration {
                        enum detail;
                    }
                }                  //detail
            }
            container show_bgp_all_community_route-filter-translated-v6_exact-match_json {
                leaf detail {
                    type enumeration {
                        enum detail;
                    }
                }                  //detail
            }
            container show_bgp_all_community_route-filter-translated-v4_exact-match_json {
                leaf detail {
                    type enumeration {
                        enum detail;
                    }
                }                  //detail
            }
            container show_bgp_all_summary_established_terse_wide {
                leaf json {
                    type enumeration {
                        enum json;
                    }
                }                  //json
            }
            container show_bgp_all_summary_failed_terse_wide {
                leaf json {
                    type enumeration {
                        enum json;
                    }
                }                  //json
            }
            container show_bgp_l2vpn_evpn_summary_established_terse {
                leaf json {
                    type enumeration {
                        enum json;
                    }
                }                  //json
            }
            container show_bgp_l2vpn_evpn_summary_established_wide {
                leaf json {
                    type enumeration {
                        enum json;
                    }
                }                  //json
            }
            container show_bgp_l2vpn_evpn_summary_failed_terse {
                leaf json {
                    type enumeration {
                        enum json;
                    }
                }                  //json
            }
            container show_bgp_l2vpn_evpn_summary_failed_wide {
                leaf json {
                    type enumeration {
                        enum json;
                    }
                }                  //json
            }
            container show_bgp_l2vpn_evpn_summary_terse_wide {
                leaf json {
                    type enumeration {
                        enum json;
                    }
                }                  //json
            }
            container show_bgp_l2vpn_evpn_route_vni_all {
                leaf vtep {
                    type enumeration {
                        enum vtep;
                    }
                }                  //vtep
                leaf REMOTE_VTEP_IP_ADDRESS {
                    type inet:ipv4-address;
                }                  //A.B.C.D
                leaf json {
                    type enumeration {
                        enum json;
                    }
                }                  //json
            }
            container debug_bgp_updates_prefix_l2vpn_evpn_type {
                leaf CHOICE_CASE {
                    type enumeration {
                        enum macip;
                        enum 2;
                    }
                }                  //<macip|2> ['MAC-IP (Type-2) route', 'MAC-IP (Type-2) route']
                leaf mac {
                    type enumeration {
                        enum mac;
                    }
                }                  //mac
                leaf MAC_ADDRESS {
                    type union {
                        type string;
                        type string;
                    }
                }                  //<X:X:X:X:X:X|X:X:X:X:X:X/M>
                leaf ip {
                    type enumeration {
                        enum ip;
                    }
                }                  //ip
                leaf IP_ADDRESS {
                    type union {
                        type inet:ipv4-address;
                        type inet:ipv6-address;
                    }
                }                  //<A.B.C.D|X:X::X:X>
                leaf IPV4_PREFIX {
                    type union {
                        type inet:ipv4-prefix;
                        type inet:ipv6-prefix;
                    }
                }                  //<A.B.C.D/M|X:X::X:X/M>
            }
            container no_debug_bgp_updates_prefix_l2vpn_evpn_type {
                leaf CHOICE_CASE {
                    type enumeration {
                        enum macip;
                        enum 2;
                    }
                }                  //<macip|2> ['MAC-IP (Type-2) route', 'MAC-IP (Type-2) route']
                leaf mac {
                    type enumeration {
                        enum mac;
                    }
                }                  //mac
                leaf MAC_ADDRESS {
                    type union {
                        type string;
                        type string;
                    }
                }                  //<X:X:X:X:X:X|X:X:X:X:X:X/M>
                leaf ip {
                    type enumeration {
                        enum ip;
                    }
                }                  //ip
                leaf IP_ADDRESS {
                    type union {
                        type inet:ipv4-address;
                        type inet:ipv6-address;
                    }
                }                  //<A.B.C.D|X:X::X:X>
                leaf IPV4_PREFIX {
                    type union {
                        type inet:ipv4-prefix;
                        type inet:ipv6-prefix;
                    }
                }                  //<A.B.C.D/M|X:X::X:X/M>
            }
            container show_ip_bgp_all_community_local-AS_exact-match_json {
                leaf detail {
                    type enumeration {
                        enum detail;
                    }
                }                  //detail
            }
            container show_ip_bgp_all_community_no-advertise_exact-match_json {
                leaf detail {
                    type enumeration {
                        enum detail;
                    }
                }                  //detail
            }
            container show_ip_bgp_all_community_no-export_exact-match_json {
                leaf detail {
                    type enumeration {
                        enum detail;
                    }
                }                  //detail
            }
            container show_ip_bgp_all_community_graceful-shutdown_exact-match_json {
                leaf detail {
                    type enumeration {
                        enum detail;
                    }
                }                  //detail
            }
            container show_ip_bgp_all_community_no-peer_exact-match_json {
                leaf detail {
                    type enumeration {
                        enum detail;
                    }
                }                  //detail
            }
            container show_ip_bgp_all_community_blackhole_exact-match_json {
                leaf detail {
                    type enumeration {
                        enum detail;
                    }
                }                  //detail
            }
            container show_ip_bgp_all_community_llgr-stale_exact-match_json {
                leaf detail {
                    type enumeration {
                        enum detail;
                    }
                }                  //detail
            }
            container show_ip_bgp_all_community_no-llgr_exact-match_json {
                leaf detail {
                    type enumeration {
                        enum detail;
                    }
                }                  //detail
            }
            container show_ip_bgp_all_community_accept-own_exact-match_json {
                leaf detail {
                    type enumeration {
                        enum detail;
                    }
                }                  //detail
            }
            container show_ip_bgp_all_community_accept-own-nexthop_exact-match_json {
                leaf detail {
                    type enumeration {
                        enum detail;
                    }
                }                  //detail
            }
            container show_ip_bgp_all_community_route-filter-v6_exact-match_json {
                leaf detail {
                    type enumeration {
                        enum detail;
                    }
                }                  //detail
            }
            container show_ip_bgp_all_community_route-filter-v4_exact-match_json {
                leaf detail {
                    type enumeration {
                        enum detail;
                    }
                }                  //detail
            }
            container show_ip_bgp_all_community_route-filter-translated-v6_exact-match_json {
                leaf detail {
                    type enumeration {
                        enum detail;
                    }
                }                  //detail
            }
            container show_ip_bgp_all_community_route-filter-translated-v4_exact-match_json {
                leaf detail {
                    type enumeration {
                        enum detail;
                    }
                }                  //detail
            }
            container show_ip_bgp_all_summary_established_terse_wide {
                leaf json {
                    type enumeration {
                        enum json;
                    }
                }                  //json
            }
            container show_ip_bgp_all_summary_failed_terse_wide {
                leaf json {
                    type enumeration {
                        enum json;
                    }
                }                  //json
            }
            container show_ip_pim_mlag_vrf_all_interface_detail {
                leaf json {
                    type enumeration {
                        enum json;
                    }
                }                  //json
            }
            container show_bgp_l2vpn_evpn_summary_established_terse_wide {
                leaf json {
                    type enumeration {
                        enum json;
                    }
                }                  //json
            }
            container show_bgp_l2vpn_evpn_summary_failed_terse_wide {
                leaf json {
                    type enumeration {
                        enum json;
                    }
                }                  //json
            }
            container show_bgp_l2vpn_evpn_route_vni_all_detail {
                leaf vtep {
                    type enumeration {
                        enum vtep;
                    }
                }                  //vtep
                leaf REMOTE_VTEP_IP_ADDRESS {
                    type inet:ipv4-address;
                }                  //A.B.C.D
                leaf json {
                    type enumeration {
                        enum json;
                    }
                }                  //json
            }
        }

    }
}
