module sonic-frr-vrrp {
    namespace "http://github.com/sonic-net/frr/sonic-frr-vrrp";
    prefix frr-vrrp;
    yang-version 1.1;

    import ietf-inet-types {
        prefix inet;
    }

    organization
        "SONiC";

    contact
        "SONiC";

    description
        "SONIC frr-vrrp FRR YANG";

    revision 2024-12-23 {
        description
            "Initial revision.";
    }
    container sonic-frr-vrrp {

    }
}
