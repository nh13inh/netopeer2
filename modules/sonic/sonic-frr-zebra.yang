module sonic-frr-zebra {
    namespace "http://github.com/sonic-net/frr/sonic-frr-zebra";
    prefix frr-zebra;
    yang-version 1.1;

    import ietf-inet-types {
        prefix inet;
    }

    organization
        "SONiC";

    contact
        "SONiC";

    description
        "SONIC frr-zebra FRR YANG";

    revision 2024-12-23 {
        description
            "Initial revision.";
    }
    container sonic-frr-zebra {

    }
}
