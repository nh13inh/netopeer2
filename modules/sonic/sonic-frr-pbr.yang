module sonic-frr-pbr {
    namespace "http://github.com/sonic-net/frr/sonic-frr-pbr";
    prefix frr-pbr;
    yang-version 1.1;

    import ietf-inet-types {
        prefix inet;
    }

    organization
        "SONiC";

    contact
        "SONiC";

    description
        "SONIC frr-pbr FRR YANG";

    revision 2024-12-23 {
        description
            "Initial revision.";
    }
    container sonic-frr-pbr {
        container PBRMAP_NODE {
            list MATCH {
                key "PREFIX";
                leaf PREFIX {
                    type string; 
                } 
                leaf dscp {
                    type enumeration {
                        enum dscp;
                    }
                }                  //dscp
                leaf DSCP_VALUE_OR_STANDARD {
                    type string;
                }                  //DSCP
                leaf dst-ip {
                    type enumeration {
                        enum dst-ip;
                    }
                }                  //dst-ip
                leaf IPV4_PREFIX {
                    type union {
                        type inet:ipv4-prefix;
                        type inet:ipv6-prefix;
                    }
                }                  //<A.B.C.D/M|X:X::X:X/M>
                leaf dst-port {
                    type enumeration {
                        enum dst-port;
                    }
                }                  //dst-port
                leaf THE_DESTINATION_PORT {
                    type int32;
                }                  //(1-65535)
                leaf ecn {
                    type enumeration {
                        enum ecn;
                    }
                }                  //ecn
                leaf EXPLICIT_CONGESTION_NOTIFICATION {
                    type int32;
                }                  //(0-3)
                leaf mark {
                    type enumeration {
                        enum mark;
                    }
                }                  //mark
                leaf MARK {
                    type int32;
                }                  //(1-4294967295)
                leaf src-ip {
                    type enumeration {
                        enum src-ip;
                    }
                }                  //src-ip
                leaf src-port {
                    type enumeration {
                        enum src-port;
                    }
                }                  //src-port
                leaf THE_SOURCE_PORT {
                    type int32;
                }                  //(1-65535)
            }
            list SET {
                key "PREFIX";
                leaf PREFIX {
                    type string; 
                } 
                leaf pcp {
                    type enumeration {
                        enum pcp;
                    }
                }                  //pcp
                leaf A_VALID_VALUE_IN {
                    type int32;
                }                  //(0-7)
                leaf queue-id {
                    type enumeration {
                        enum queue-id;
                    }
                }                  //queue-id
                leaf vlan {
                    type enumeration {
                        enum vlan;
                    }
                }                  //vlan
                leaf nexthop-group {
                    type enumeration {
                        enum nexthop-group;
                    }
                }                  //nexthop-group
                leaf THE_NAME_OF_THE {
                    type string;
                }                  //NHGNAME
                leaf vrf {
                    type enumeration {
                        enum vrf;
                    }
                }                  //vrf
                leaf THE_VRF_NAME {
                    type string;
                }                  //NAME
                leaf unchanged {
                    type enumeration {
                        enum unchanged;
                    }
                }
            }
            list STRIP {
                key "PREFIX";
                leaf PREFIX {
                    type string; 
                } 
                leaf vlan {
                    type enumeration {
                        enum vlan;
                    }
                }                  //vlan
            }
            list NO_MATCH {
                key "PREFIX";
                leaf PREFIX {
                    type string; 
                } 
                leaf dscp {
                    type enumeration {
                        enum dscp;
                    }
                }                  //dscp
                leaf DSCP_VALUE_OR_STANDARD {
                    type string;
                }                  //DSCP
                leaf dst-ip {
                    type enumeration {
                        enum dst-ip;
                    }
                }                  //dst-ip
                leaf IPV4_PREFIX {
                    type union {
                        type inet:ipv4-prefix;
                        type inet:ipv6-prefix;
                    }
                }                  //<A.B.C.D/M|X:X::X:X/M>
                leaf dst-port {
                    type enumeration {
                        enum dst-port;
                    }
                }                  //dst-port
                leaf THE_DESTINATION_PORT {
                    type int32;
                }                  //(1-65535)
                leaf ecn {
                    type enumeration {
                        enum ecn;
                    }
                }                  //ecn
                leaf EXPLICIT_CONGESTION_NOTIFICATION {
                    type int32;
                }                  //(0-3)
                leaf mark {
                    type enumeration {
                        enum mark;
                    }
                }                  //mark
                leaf MARK {
                    type int32;
                }                  //(1-4294967295)
                leaf src-ip {
                    type enumeration {
                        enum src-ip;
                    }
                }                  //src-ip
                leaf src-port {
                    type enumeration {
                        enum src-port;
                    }
                }                  //src-port
                leaf THE_SOURCE_PORT {
                    type int32;
                }                  //(1-65535)
            }
            list NO_SET {
                key "PREFIX";
                leaf PREFIX {
                    type string; 
                } 
                leaf pcp {
                    type enumeration {
                        enum pcp;
                    }
                }                  //pcp
                leaf A_VALID_VALUE_IN {
                    type int32;
                }                  //(0-7)
                leaf queue-id {
                    type enumeration {
                        enum queue-id;
                    }
                }                  //queue-id
                leaf vlan {
                    type enumeration {
                        enum vlan;
                    }
                }                  //vlan
            }
            list NO_STRIP {
                key "PREFIX";
                leaf PREFIX {
                    type string; 
                } 
                leaf vlan {
                    type enumeration {
                        enum vlan;
                    }
                }                  //vlan
            }
            list MATCH_IP-PROTOCOL {
                key "PREFIX";
                leaf PREFIX {
                    type string; 
                } 
                leaf tcp {
                    type enumeration {
                        enum tcp;
                    }
                }                  //tcp
                leaf udp {
                    type enumeration {
                        enum udp;
                    }
                }                  //udp
            }
            list SET_NEXTHOP {
                key "PREFIX";
                leaf PREFIX {
                    type string; 
                } 
                leaf IP_ADDRESS {
                    type union {
                        type inet:ipv4-address;
                        type inet:ipv6-address;
                    }
                }                  //<A.B.C.D|X:X::X:X>
                leaf INTERFACE_TO_USE {
                    type string;
                }                  //INTERFACE
                leaf nexthop-vrf {
                    type enumeration {
                        enum nexthop-vrf;
                    }
                }                  //nexthop-vrf
                leaf THE_NEXTHOP-VRF_NAME {
                    type string;
                }                  //NAME
            }
            list NO_MATCH_IP-PROTOCOL {
                key "PREFIX";
                leaf PREFIX {
                    type string; 
                } 
                leaf tcp {
                    type enumeration {
                        enum tcp;
                    }
                }                  //tcp
                leaf udp {
                    type enumeration {
                        enum udp;
                    }
                }                  //udp
            }
            list NO_SET_NEXTHOP {
                key "PREFIX";
                leaf PREFIX {
                    type string; 
                } 
                leaf IP_ADDRESS {
                    type union {
                        type inet:ipv4-address;
                        type inet:ipv6-address;
                    }
                }                  //<A.B.C.D|X:X::X:X>
                leaf INTERFACE_TO_USE {
                    type string;
                }                  //INTERFACE
                leaf nexthop-vrf {
                    type enumeration {
                        enum nexthop-vrf;
                    }
                }                  //nexthop-vrf
                leaf THE_NEXTHOP-VRF_NAME {
                    type string;
                }                  //NAME
            }
            list NO_SET_NEXTHOP-GROUP {
                key "PREFIX";
                leaf PREFIX {
                    type string; 
                } 
                leaf THE_NAME_OF_THE {
                    type string;
                }                  //NHGNAME
            }
            list NO_SET_VRF {
                key "PREFIX";
                leaf PREFIX {
                    type string; 
                } 
                leaf THE_VRF_NAME {
                    type string;
                }                  //NAME
                leaf unchanged {
                    type enumeration {
                        enum unchanged;
                    }
                }
            }
        }

    }
}
