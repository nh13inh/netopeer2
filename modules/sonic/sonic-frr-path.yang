module sonic-frr-path {
    namespace "http://github.com/sonic-net/frr/sonic-frr-path";
    prefix frr-path;
    yang-version 1.1;

    import ietf-inet-types {
        prefix inet;
    }

    organization
        "SONiC";

    contact
        "SONiC";

    description
        "SONIC frr-path FRR YANG";

    revision 2024-12-23 {
        description
            "Initial revision.";
    }
    container sonic-frr-path {

    }
}
